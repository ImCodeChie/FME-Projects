FME workspace Data_prep_clipping.fmw

Parameters:
- SourceDataset_OGCGEOPACKAGE_3 = ""$(FME_MF_DIR)Argentina\Vectors\Reference\argentina_strat174389_3857_std0000000000-0000000000.gpkg" "$(FME_MF_DIR)Argentina\Vectors\Reference\argentina_strat176123_3857_std00000000000000000000.gpkg" "$(FME_MF_DIR)Argentina\Vectors\Reference\argentina_strat176606_3857_std00000000000000000000.gpkg" "$(FME_MF_DIR)Argentina\Vectors\Reference\argentina_strat176608_3857_std00000000000000000000.gpkg" "$(FME_MF_DIR)Argentina\Vectors\Reference\argentina_strat176635_3857_std0000000000-0000000000.gpkg" "$(FME_MF_DIR)Argentina\Vectors\Reference\argentina_strat180082_3857_std0000000000-0000000000.gpkg""   # GeoPackage File
- DestDataset_OGCGEOPACKAGE = $(FME_MF_DIR)result   # GeoPackage File
- DestDataset_SHAPEFILE = $(FME_MF_DIR)result\clipped_tiles\Shapefile   # Destination Esri Shapefile Folder
- SourceDataset_OGCGEOPACKAGE = ""$(FME_MF_DIR)Vectors\Reference\2022\Europe-REF_7474_2022_Mediterranean_Forests_Woodlands_Scrub.gpkg" "$(FME_MF_DIR)Vectors\Reference\2022\Europe-REF_8004_2022_Boreal_Forests_Taiga.gpkg" "$(FME_MF_DIR)Vectors\Reference\2022\Europe-REF_11539_2022_Boreal_Forests_Taiga.gpkg" "$(FME_MF_DIR)Vectors\Reference\2022\Europe-REF_11639_2022_Mediterranean_Forests_Woodlands_Scrub.gpkg" "$(FME_MF_DIR)Vectors\Reference\2022\Europe-REF-280_2022_Temperate_Broadleaf_Mixed_Forests.gpkg" "$(FME_MF_DIR)Vectors\Reference\2022\Europe-REF-393_2022_Mediterranean_Forests_Woodlands_Scrub.gpkg" "$(FME_MF_DIR)Vectors\Reference\2022\Europe-REF-598_2022_Mediterranean_Forests_Woodlands_Scrub.gpkg" "$(FME_MF_DIR)Vectors\Reference\2022\Europe-REF-1048_2022_Mediterranean_Forests_Woodlands_Scrub.gpkg" "$(FME_MF_DIR)Vectors\Reference\2022\Europe-REF-2018_2022_Mediterranean_Forests_Woodlands_Scrub.gpkg" "$(FME_MF_DIR)Vectors\Reference\2022\Europe-REF-3307_2022_Temperate_Broadleaf_Mixed_Forests.gpkg" "$(FME_MF_DIR)Vectors\Reference\2022\Europe-REF-3544_2022_Temperate_Broadleaf_Mixed_Forests.gpkg" "$(FME_MF_DIR)Vectors\Reference\2022\Europe-REF-3790_2022_Temperate_Broadleaf_Mixed_Forests.gpkg" "$(FME_MF_DIR)Vectors\Reference\2022\Europe-REF-4614_2022_Temperate_Broadleaf_Mixed_Forests.gpkg" "$(FME_MF_DIR)Vectors\Reference\2022\Europe-REF-5008_2022_Temperate_Broadleaf_Mixed_Forests.gpkg" "$(FME_MF_DIR)Vectors\Reference\2022\Europe-REF-5150_2022_Temperate_Broadleaf_Mixed_Forests.gpkg" "$(FME_MF_DIR)Vectors\Reference\2022\Europe-REF-5470_2022_Mediterranean_Forests_Woodlands_Scrub.gpkg" "$(FME_MF_DIR)Vectors\Reference\2022\Europe-REF-5952_2022_Temperate_Broadleaf_Mixed_Forests.gpkg" "$(FME_MF_DIR)Vectors\Reference\2022\Europe-REF-15042_2022_Flooded_Grasslands_Savannas.gpkg" "$(FME_MF_DIR)Vectors\Reference\2022\Europe-REF-15315_2022_Temperate_Broadleaf_Mixed_Forests.gpkg" "$(FME_MF_DIR)Vectors\Reference\2022\Europe-REF-15719_2022_Boreal_Forests_Taiga.gpkg" "$(FME_MF_DIR)Vectors\Reference\2022\Europe-REF-18599_2022_Temperate_Broadleaf_Mixed_Forests.gpkg" "$(FME_MF_DIR)Vectors\Reference\2022\Europe-REF-18757_2022_Temperate_Grasslands_Savannas_Shrublands.gpkg" "$(FME_MF_DIR)Vectors\Reference\2022\Europe-REF-21171_2022_Temperate_Broadleaf_Mixed_Forests.gpkg" "$(FME_MF_DIR)Vectors\Reference\2022\Europe-REF-21540_2022_Temperate_Grasslands_Savannas_Shrublands.gpkg" "$(FME_MF_DIR)Vectors\Reference\2022\Europe-REF-22993_2022_Temperate_Grasslands_Savannas_Shrublands.gpkg" "$(FME_MF_DIR)Vectors\Reference\2022\Europe-REF-23736_2022_Deserts_Xeric_Shrublands.gpkg" "$(FME_MF_DIR)Vectors\Reference\2022\Europe-REF-25006_2022_Deserts_Xeric_Shrublands.gpkg" "$(FME_MF_DIR)Vectors\Reference\2022\Europe-REF-32582_2022_Temperate_Grasslands_Savannas_Shrublands.gpkg" "$(FME_MF_DIR)Vectors\Reference\2022\Europe-REF-34531_2022_Deserts_Xeric_Shrublands.gpkg" "$(FME_MF_DIR)Vectors\Reference\2022\Europe-REF-42077_2022_Temperate_Grasslands_Savannas_Shrublands.gpkg" "$(FME_MF_DIR)Vectors\Reference\2022\Europe-REF-44674_2022_Temperate_Grasslands_Savannas_Shrublands.gpkg""   # GeoPackage File
- DestDataset_SHAPEFILE_3 = $(FME_MF_DIR)result\ML_outputs\Shapefile   # Destination Esri Shapefile Folder
- SourceDataset_OGCGEOPACKAGE_9 = ""C:\Users\lyi\Desktop\CLU_Aassessment\Europe\ml\Albania\*.gpkg" "C:\Users\lyi\Desktop\CLU_Aassessment\Europe\ml\Austria\*.gpkg" "C:\Users\lyi\Desktop\CLU_Aassessment\Europe\ml\Belarus\*.gpkg" "C:\Users\lyi\Desktop\CLU_Aassessment\Europe\ml\Belgium\*.gpkg" "C:\Users\lyi\Desktop\CLU_Aassessment\Europe\ml\Bosnia-and-Herzegovina\*.gpkg" "C:\Users\lyi\Desktop\CLU_Aassessment\Europe\ml\Czechia\*.gpkg" "C:\Users\lyi\Desktop\CLU_Aassessment\Europe\ml\Germany\*.gpkg" "C:\Users\lyi\Desktop\CLU_Aassessment\Europe\ml\Italy\*.gpkg" "C:\Users\lyi\Desktop\CLU_Aassessment\Europe\ml\Kosovo\*.gpkg" "C:\Users\lyi\Desktop\CLU_Aassessment\Europe\ml\Liechtenstein\*.gpkg" "C:\Users\lyi\Desktop\CLU_Aassessment\Europe\ml\Luxembourg\*.gpkg" "C:\Users\lyi\Desktop\CLU_Aassessment\Europe\ml\Malta\*.gpkg" "C:\Users\lyi\Desktop\CLU_Aassessment\Europe\ml\Netherlands_fb\*.gpkg" "C:\Users\lyi\Desktop\CLU_Aassessment\Europe\ml\Switzerland\*.gpkg""   # GeoPackage File
- FEATURE_TYPES =
- SourceDataset_OGCGEOPACKAGE_7 = C:\Users\lyi\Downloads\gadm_410-gpkg\gadm_410.gpkg   # GeoPackage File
- SourceDataset_OGCGEOPACKAGE_8 = ""$(FME_MF_DIR)ml\Croatia_17__Varazdinska__field-borders.gpkg" "$(FME_MF_DIR)ml\Denmark_1_1_Hovedstaden_Albertslund_field-borders.gpkg" "$(FME_MF_DIR)ml\Denmark_4_5_Sjaelland_Kalundborg_field-borders.gpkg" "$(FME_MF_DIR)ml\Denmark_5_4_Syddanmark_Billund_field-borders.gpkg" "$(FME_MF_DIR)ml\Estonia_3_22_Ida-Viru_Vaivara_field-borders.gpkg" "$(FME_MF_DIR)ml\Estonia_13_20_Tartu_Vara_field-borders.gpkg" "$(FME_MF_DIR)ml\France_11_5_Occitanie_Gers_field-borders.gpkg" "$(FME_MF_DIR)ml\France_12_5_Pays-de-la-Loire_Vendee_field-borders.gpkg" "$(FME_MF_DIR)ml\Hungary_2_4_Baranya_Pecsvaradi_field-borders.gpkg" "$(FME_MF_DIR)ml\Hungary_20_5_Zala_Pacsa-Zalaegerszeg_field-borders.gpkg" "$(FME_MF_DIR)ml\Italy_11_1_Marche_Ancona_field-borders.gpkg" "$(FME_MF_DIR)ml\Italy_11_4_Marche_Macerata_field-borders.gpkg" "$(FME_MF_DIR)ml\Italy_13_5_Piemonte_Novara_field-borders.gpkg" "$(FME_MF_DIR)ml\Norway_2_4_Astfold_Eidsberg_field-borders.gpkg" "$(FME_MF_DIR)ml\Norway_2_14_Astfold_Rakkestad_field-borders.gpkg" "$(FME_MF_DIR)ml\Norway_5_16_Finnmark_Sor-Varanger_field-borders.gpkg" "$(FME_MF_DIR)ml\Norway_13_3_Rogaland_Eigersund_field-borders.gpkg" "$(FME_MF_DIR)ml\Norway_13_13_Rogaland_Lund_field-borders.gpkg" "$(FME_MF_DIR)ml\Norway_14_23_Sogn-og-Fjordane_Solund_field-borders.gpkg" "$(FME_MF_DIR)ml\Portugal_3_1_Beja_Aljustrel_field-borders.gpkg" "$(FME_MF_DIR)ml\Portugal_3_2_Beja_Almodovar_field-borders.gpkg" "$(FME_MF_DIR)ml\Portugal_3_3_Beja_Alvito_field-borders.gpkg" "$(FME_MF_DIR)ml\Portugal_3_4_Beja_Barrancos_field-borders.gpkg" "$(FME_MF_DIR)ml\Portugal_3_5_Beja_Beja_field-borders.gpkg" "$(FME_MF_DIR)ml\Portugal_3_6_Beja_Castro-Verde_field-borders.gpkg" "$(FME_MF_DIR)ml\Portugal_3_7_Beja_Cuba_field-borders.gpkg" "$(FME_MF_DIR)ml\Portugal_3_8_Beja_Ferreira-do-Alentejo_field-borders.gpkg" "$(FME_MF_DIR)ml\Portugal_3_9_Beja_Mertola_field-borders.gpkg" "$(FME_MF_DIR)ml\Portugal_3_10_Beja_Moura_field-borders.gpkg" "$(FME_MF_DIR)ml\Portugal_3_11_Beja_Odemira_field-borders.gpkg" "$(FME_MF_DIR)ml\Portugal_3_12_Beja_Ourique_field-borders.gpkg" "$(FME_MF_DIR)ml\Portugal_3_13_Beja_Serpa_field-borders.gpkg" "$(FME_MF_DIR)ml\Portugal_3_14_Beja_Vidigueira_field-borders.gpkg" "$(FME_MF_DIR)ml\Spain_4_3_1_Castilla-La-Mancha_Cuenca_field-borders.gpkg" "$(FME_MF_DIR)ml\Spain_4_3_2_Castilla-La-Mancha_Cuenca_field-borders.gpkg" "$(FME_MF_DIR)ml\Spain_4_3_3_Castilla-La-Mancha_Cuenca_field-borders.gpkg" "$(FME_MF_DIR)ml\Spain_4_3_4_Castilla-La-Mancha_Cuenca_field-borders.gpkg" "$(FME_MF_DIR)ml\Spain_4_3_5_Castilla-La-Mancha_Cuenca_field-borders.gpkg" "$(FME_MF_DIR)ml\Spain_4_3_6_Castilla-La-Mancha_Cuenca_field-borders.gpkg" "$(FME_MF_DIR)ml\Spain_4_3_7_Castilla-La-Mancha_Cuenca_field-borders.gpkg""   # GeoPackage File
- FEATURE_TYPES_2 =

Readers:
- OGCGEOPACKAGE_2: OGCGEOPACKAGE from $(SourceDataset_OGCGEOPACKAGE_3)
- OGCGEOPACKAGE_1: OGCGEOPACKAGE from $(SourceDataset_OGCGEOPACKAGE)
- OGCGEOPACKAGE_5: OGCGEOPACKAGE from $(SourceDataset_OGCGEOPACKAGE_9)
- OGCGEOPACKAGE_4: OGCGEOPACKAGE from $(SourceDataset_OGCGEOPACKAGE_7)
- OGCGEOPACKAGE_6: OGCGEOPACKAGE from $(SourceDataset_OGCGEOPACKAGE_8)

Writers:
- OGCGEOPACKAGE_3: OGCGEOPACKAGE to $(DestDataset_OGCGEOPACKAGE)
- SHAPEFILE_1: SHAPEFILE to $(DestDataset_SHAPEFILE)
- SHAPEFILE_2: SHAPEFILE to $(DestDataset_SHAPEFILE_3)

Europe-REF_1048_2022_Mediterranean_Forests_Woodlands_Scrub (reader OGCGEOPACKAGE_1)
    attributes: ASE_annota double, ESA_Class text(254), Area_Crop double, Sum_Area text(200), Crop_Perce text(200), Keep text(200), cat int, fid int,PrimaryKey
    -> Reprojector_14
Reprojector_14
    DEST = EPSG:4326
    INTERPOLATION_TYPE_NAME = Nearest Neighbor
    RASTER_CELL_SIZE = Preserve Cells
    RASTER_TOLERANCE = 0.0
    REPROJECTED -> BoundingBoxAccumulator_41
BoundingBoxAccumulator_41
    ACCUM_ATTRS_NAME = Merge Incoming Attributes
    BOUNDING_BOX -> DL_fieldborders_ARG.6.17_Argentina_Cordoba_Rio-Segundo_EDA (writer SHAPEFILE_1)
    BOUNDING_BOX -> Clipper_21 [CLIPPER]
    BOUNDING_BOX -> Clipper [CANDIDATE]
Europe-REF_2018_2022_Mediterranean_Forests_Woodlands_Scrub (reader OGCGEOPACKAGE_1)
    attributes: ASE_annota double, ESA_Class text(254), Area_Crop double, Sum_Area text(200), Crop_Perce text(200), Keep text(200), cat int, fid int,PrimaryKey
    -> Reprojector_15
Reprojector_15
    DEST = EPSG:4326
    INTERPOLATION_TYPE_NAME = Nearest Neighbor
    RASTER_CELL_SIZE = Preserve Cells
    RASTER_TOLERANCE = 0.0
    REPROJECTED -> BoundingBoxAccumulator_42
BoundingBoxAccumulator_42
    ACCUM_ATTRS_NAME = Merge Incoming Attributes
    BOUNDING_BOX -> DL_fieldborders_ARG.6.17_Argentina_Cordoba_Rio-Segundo_EDA (writer SHAPEFILE_1)
    BOUNDING_BOX -> Clipper_20 [CLIPPER]
    BOUNDING_BOX -> Clipper [CANDIDATE]
Europe-REF_5470_2022_Mediterranean_Forests_Woodlands_Scrub (reader OGCGEOPACKAGE_1)
    attributes: ASE_annota double, ESA_Class text(254), Area_Crop double, Sum_Area text(200), Crop_Perce text(200), Keep text(200), cat int, fid int,PrimaryKey
    -> Reprojector_16
Reprojector_16
    DEST = EPSG:4326
    INTERPOLATION_TYPE_NAME = Nearest Neighbor
    RASTER_CELL_SIZE = Preserve Cells
    RASTER_TOLERANCE = 0.0
    REPROJECTED -> BoundingBoxAccumulator_43
BoundingBoxAccumulator_43
    ACCUM_ATTRS_NAME = Merge Incoming Attributes
    BOUNDING_BOX -> DL_fieldborders_ARG.6.17_Argentina_Cordoba_Rio-Segundo_EDA (writer SHAPEFILE_1)
    BOUNDING_BOX -> Clipper_23 [CLIPPER]
    BOUNDING_BOX -> Clipper [CANDIDATE]
Europe-REF_7474_2022_Mediterranean_Forests_Woodlands_Scrub (reader OGCGEOPACKAGE_1)
    attributes: ASE_annota double, ESA_Class text(254), Area_Crop double, Sum_Area text(200), Crop_Perce text(200), Keep text(200), cat int, fid int,PrimaryKey
    -> Reprojector_17
Reprojector_17
    DEST = EPSG:4326
    INTERPOLATION_TYPE_NAME = Nearest Neighbor
    RASTER_CELL_SIZE = Preserve Cells
    RASTER_TOLERANCE = 0.0
    REPROJECTED -> BoundingBoxAccumulator_44
BoundingBoxAccumulator_44
    ACCUM_ATTRS_NAME = Merge Incoming Attributes
    BOUNDING_BOX -> DL_fieldborders_ARG.6.17_Argentina_Cordoba_Rio-Segundo_EDA (writer SHAPEFILE_1)
    BOUNDING_BOX -> Clipper_22 [CLIPPER]
    BOUNDING_BOX -> Clipper [CANDIDATE]
Europe-REF_11639_2022_Mediterranean_Forests_Woodlands_Scrub (reader OGCGEOPACKAGE_1)
    attributes: ASE_annota double, ESA_Class text(254), Area_Crop double, Sum_Area text(200), Crop_Perce text(200), Keep text(200), cat int, fid int,PrimaryKey
    -> Reprojector_20
Reprojector_20
    DEST = EPSG:4326
    INTERPOLATION_TYPE_NAME = Nearest Neighbor
    RASTER_CELL_SIZE = Preserve Cells
    RASTER_TOLERANCE = 0.0
    REPROJECTED -> BoundingBoxAccumulator_47
BoundingBoxAccumulator_47
    ACCUM_ATTRS_NAME = Merge Incoming Attributes
    BOUNDING_BOX -> DL_fieldborders_ARG.6.17_Argentina_Cordoba_Rio-Segundo_EDA (writer SHAPEFILE_1)
    BOUNDING_BOX -> Clipper_27 [CLIPPER]
    BOUNDING_BOX -> Clipper [CANDIDATE]
Europe-REF_18757_2022_Temperate_Grasslands_Savannas_Shrublands (reader OGCGEOPACKAGE_1)
    attributes: ASE_annota double, ESA_Class text(254), Area_Crop double, Sum_Area text(200), Crop_Perce text(200), Keep text(200), cat int, fid int,PrimaryKey
    -> Reprojector_24
Reprojector_24
    DEST = EPSG:4326
    INTERPOLATION_TYPE_NAME = Nearest Neighbor
    RASTER_CELL_SIZE = Preserve Cells
    RASTER_TOLERANCE = 0.0
    REPROJECTED -> BoundingBoxAccumulator_12
BoundingBoxAccumulator_12
    ACCUM_ATTRS_NAME = Merge Incoming Attributes
    BOUNDING_BOX -> DL_fieldborders_ARG.6.17_Argentina_Cordoba_Rio-Segundo_EDA (writer SHAPEFILE_1)
    BOUNDING_BOX -> Clipper_29 [CLIPPER]
    BOUNDING_BOX -> Clipper [CANDIDATE]
Europe-REF_21540_2022_Temperate_Grasslands_Savannas_Shrublands (reader OGCGEOPACKAGE_1)
    attributes: ASE_annota double, ESA_Class text(254), Area_Crop double, Sum_Area text(200), Crop_Perce text(200), Keep text(200), cat int, fid int,PrimaryKey
    -> Reprojector_25
Reprojector_25
    DEST = EPSG:4326
    INTERPOLATION_TYPE_NAME = Nearest Neighbor
    RASTER_CELL_SIZE = Preserve Cells
    RASTER_TOLERANCE = 0.0
    REPROJECTED -> BoundingBoxAccumulator_13
BoundingBoxAccumulator_13
    ACCUM_ATTRS_NAME = Merge Incoming Attributes
    BOUNDING_BOX -> DL_fieldborders_ARG.6.17_Argentina_Cordoba_Rio-Segundo_EDA (writer SHAPEFILE_1)
    BOUNDING_BOX -> Clipper_32 [CLIPPER]
    BOUNDING_BOX -> Clipper [CANDIDATE]
Europe-REF_22993_2022_Temperate_Grasslands_Savannas_Shrublands (reader OGCGEOPACKAGE_1)
    attributes: ASE_annota double, ESA_Class text(254), Area_Crop double, Sum_Area text(200), Crop_Perce text(200), Keep text(200), cat int, fid int,PrimaryKey
    -> Reprojector_26
Reprojector_26
    DEST = EPSG:4326
    INTERPOLATION_TYPE_NAME = Nearest Neighbor
    RASTER_CELL_SIZE = Preserve Cells
    RASTER_TOLERANCE = 0.0
    REPROJECTED -> BoundingBoxAccumulator_14
BoundingBoxAccumulator_14
    ACCUM_ATTRS_NAME = Merge Incoming Attributes
    BOUNDING_BOX -> DL_fieldborders_ARG.6.17_Argentina_Cordoba_Rio-Segundo_EDA (writer SHAPEFILE_1)
    BOUNDING_BOX -> Clipper_31 [CLIPPER]
    BOUNDING_BOX -> Clipper [CANDIDATE]
Europe-REF_32582_2022_Temperate_Grasslands_Savannas_Shrublands (reader OGCGEOPACKAGE_1)
    attributes: ASE_annota double, ESA_Class text(254), Area_Crop double, Sum_Area text(200), Crop_Perce text(200), Keep text(200), cat int, fid int,PrimaryKey
    -> Reprojector_29
Reprojector_29
    DEST = EPSG:4326
    INTERPOLATION_TYPE_NAME = Nearest Neighbor
    RASTER_CELL_SIZE = Preserve Cells
    RASTER_TOLERANCE = 0.0
    REPROJECTED -> BoundingBoxAccumulator_17
BoundingBoxAccumulator_17
    ACCUM_ATTRS_NAME = Merge Incoming Attributes
    BOUNDING_BOX -> DL_fieldborders_ARG.6.17_Argentina_Cordoba_Rio-Segundo_EDA (writer SHAPEFILE_1)
    BOUNDING_BOX -> Clipper_2 [CLIPPER]
    BOUNDING_BOX -> Clipper [CANDIDATE]
Europe-REF_42077_2022_Temperate_Grasslands_Savannas_Shrublands (reader OGCGEOPACKAGE_1)
    attributes: ASE_annota double, ESA_Class text(254), Area_Crop double, Sum_Area text(200), Crop_Perce text(200), Keep text(200), cat int, fid int,PrimaryKey
    -> Reprojector_31
Reprojector_31
    DEST = EPSG:4326
    INTERPOLATION_TYPE_NAME = Nearest Neighbor
    RASTER_CELL_SIZE = Preserve Cells
    RASTER_TOLERANCE = 0.0
    REPROJECTED -> BoundingBoxAccumulator_19
BoundingBoxAccumulator_19
    ACCUM_ATTRS_NAME = Merge Incoming Attributes
    BOUNDING_BOX -> DL_fieldborders_ARG.6.17_Argentina_Cordoba_Rio-Segundo_EDA (writer SHAPEFILE_1)
    BOUNDING_BOX -> Clipper_4 [CLIPPER]
    BOUNDING_BOX -> Clipper [CANDIDATE]
Europe-REF_44674_2022_Temperate_Grasslands_Savannas_Shrublands (reader OGCGEOPACKAGE_1)
    attributes: ASE_annota double, ESA_Class text(254), Area_Crop double, Sum_Area text(200), Crop_Perce text(200), Keep text(200), cat int, fid int,PrimaryKey
    -> Reprojector_32
Reprojector_32
    DEST = EPSG:4326
    INTERPOLATION_TYPE_NAME = Nearest Neighbor
    RASTER_CELL_SIZE = Preserve Cells
    RASTER_TOLERANCE = 0.0
    REPROJECTED -> BoundingBoxAccumulator_20
BoundingBoxAccumulator_20
    ACCUM_ATTRS_NAME = Merge Incoming Attributes
    BOUNDING_BOX -> DL_fieldborders_ARG.6.17_Argentina_Cordoba_Rio-Segundo_EDA (writer SHAPEFILE_1)
    BOUNDING_BOX -> Clipper_8 [CLIPPER]
    BOUNDING_BOX -> Clipper [CANDIDATE]
Europe-REF_1_2022_Temperate_Broadleaf_Mixed_Forests (reader OGCGEOPACKAGE_1)
    attributes: cst_code text, date_part double, sfd_id mediumint, Ref_year int, fid int,PrimaryKey
    -> Reprojector_2
Reprojector_2
    DEST = EPSG:4326
    INTERPOLATION_TYPE_NAME = Nearest Neighbor
    RASTER_CELL_SIZE = Preserve Cells
    RASTER_TOLERANCE = 0.0
    REPROJECTED -> BoundingBoxAccumulator_29
BoundingBoxAccumulator_29
    ACCUM_ATTRS_NAME = Merge Incoming Attributes
    BOUNDING_BOX -> DL_fieldborders_ARG.6.17_Argentina_Cordoba_Rio-Segundo_EDA (writer SHAPEFILE_1)
    BOUNDING_BOX -> Clipper_5 [CLIPPER]
    BOUNDING_BOX -> Clipper [CANDIDATE]
Europe-REF_3_2022_Temperate_Broadleaf_Mixed_Forests (reader OGCGEOPACKAGE_1)
    attributes: cst_code text, date_part double, sfd_id mediumint, Ref_year int, fid int,PrimaryKey
    -> Reprojector_3
Reprojector_3
    DEST = EPSG:4326
    INTERPOLATION_TYPE_NAME = Nearest Neighbor
    RASTER_CELL_SIZE = Preserve Cells
    RASTER_TOLERANCE = 0.0
    REPROJECTED -> BoundingBoxAccumulator_30
BoundingBoxAccumulator_30
    ACCUM_ATTRS_NAME = Merge Incoming Attributes
    BOUNDING_BOX -> DL_fieldborders_ARG.6.17_Argentina_Cordoba_Rio-Segundo_EDA (writer SHAPEFILE_1)
    BOUNDING_BOX -> Clipper_10 [CLIPPER]
    BOUNDING_BOX -> Clipper [CANDIDATE]
Europe-REF_4_2022_Temperate_Broadleaf_Mixed_Forests (reader OGCGEOPACKAGE_1)
    attributes: cst_code text, date_part double, sfd_id mediumint, Ref_year int, fid int,PrimaryKey
    -> Reprojector_4
Reprojector_4
    DEST = EPSG:4326
    INTERPOLATION_TYPE_NAME = Nearest Neighbor
    RASTER_CELL_SIZE = Preserve Cells
    RASTER_TOLERANCE = 0.0
    REPROJECTED -> BoundingBoxAccumulator_31
BoundingBoxAccumulator_31
    ACCUM_ATTRS_NAME = Merge Incoming Attributes
    BOUNDING_BOX -> DL_fieldborders_ARG.6.17_Argentina_Cordoba_Rio-Segundo_EDA (writer SHAPEFILE_1)
    BOUNDING_BOX -> Clipper_11 [CLIPPER]
    BOUNDING_BOX -> Clipper [CANDIDATE]
Europe-REF_7_2022_Temperate_Broadleaf_Mixed_Forests (reader OGCGEOPACKAGE_1)
    attributes: cst_code text, date_part double, sfd_id mediumint, Ref_year int, fid int,PrimaryKey
    -> Reprojector_5
Reprojector_5
    DEST = EPSG:4326
    INTERPOLATION_TYPE_NAME = Nearest Neighbor
    RASTER_CELL_SIZE = Preserve Cells
    RASTER_TOLERANCE = 0.0
    REPROJECTED -> BoundingBoxAccumulator_32
BoundingBoxAccumulator_32
    ACCUM_ATTRS_NAME = Merge Incoming Attributes
    BOUNDING_BOX -> DL_fieldborders_ARG.6.17_Argentina_Cordoba_Rio-Segundo_EDA (writer SHAPEFILE_1)
    BOUNDING_BOX -> Clipper_16 [CLIPPER]
    BOUNDING_BOX -> Clipper [CANDIDATE]
Europe-REF_12_2022_Temperate_Broadleaf_Mixed_Forests (reader OGCGEOPACKAGE_1)
    attributes: cst_code text, date_part double, sfd_id mediumint, Ref_year int, fid int,PrimaryKey
    -> Reprojector_6
Reprojector_6
    DEST = EPSG:4326
    INTERPOLATION_TYPE_NAME = Nearest Neighbor
    RASTER_CELL_SIZE = Preserve Cells
    RASTER_TOLERANCE = 0.0
    REPROJECTED -> BoundingBoxAccumulator_33
BoundingBoxAccumulator_33
    ACCUM_ATTRS_NAME = Merge Incoming Attributes
    BOUNDING_BOX -> DL_fieldborders_ARG.6.17_Argentina_Cordoba_Rio-Segundo_EDA (writer SHAPEFILE_1)
    BOUNDING_BOX -> Clipper_13 [CLIPPER]
    BOUNDING_BOX -> Clipper [CANDIDATE]
Europe-REF_16_2022_Temperate_Broadleaf_Mixed_Forests (reader OGCGEOPACKAGE_1)
    attributes: cst_code text, date_part double, sfd_id mediumint, Ref_year int, fid int,PrimaryKey
    -> Reprojector_7
Reprojector_7
    DEST = EPSG:4326
    INTERPOLATION_TYPE_NAME = Nearest Neighbor
    RASTER_CELL_SIZE = Preserve Cells
    RASTER_TOLERANCE = 0.0
    REPROJECTED -> BoundingBoxAccumulator_34
BoundingBoxAccumulator_34
    ACCUM_ATTRS_NAME = Merge Incoming Attributes
    BOUNDING_BOX -> DL_fieldborders_ARG.6.17_Argentina_Cordoba_Rio-Segundo_EDA (writer SHAPEFILE_1)
    BOUNDING_BOX -> Clipper_12 [CLIPPER]
    BOUNDING_BOX -> Clipper [CANDIDATE]
Europe-REF_21_2022_Temperate_Broadleaf_Mixed_Forests (reader OGCGEOPACKAGE_1)
    attributes: cst_code text, date_part double, sfd_id mediumint, Ref_year int, fid int,PrimaryKey
    -> Reprojector_8
Reprojector_8
    DEST = EPSG:4326
    INTERPOLATION_TYPE_NAME = Nearest Neighbor
    RASTER_CELL_SIZE = Preserve Cells
    RASTER_TOLERANCE = 0.0
    REPROJECTED -> BoundingBoxAccumulator_35
BoundingBoxAccumulator_35
    ACCUM_ATTRS_NAME = Merge Incoming Attributes
    BOUNDING_BOX -> DL_fieldborders_ARG.6.17_Argentina_Cordoba_Rio-Segundo_EDA (writer SHAPEFILE_1)
    BOUNDING_BOX -> Clipper_15 [CLIPPER]
    BOUNDING_BOX -> Clipper [CANDIDATE]
Europe-REF_22_2022_Temperate_Broadleaf_Mixed_Forests (reader OGCGEOPACKAGE_1)
    attributes: cst_code text, date_part double, sfd_id mediumint, Ref_year int, fid int,PrimaryKey
    -> Reprojector_9
Reprojector_9
    DEST = EPSG:4326
    INTERPOLATION_TYPE_NAME = Nearest Neighbor
    RASTER_CELL_SIZE = Preserve Cells
    RASTER_TOLERANCE = 0.0
    REPROJECTED -> BoundingBoxAccumulator_36
BoundingBoxAccumulator_36
    ACCUM_ATTRS_NAME = Merge Incoming Attributes
    BOUNDING_BOX -> DL_fieldborders_ARG.6.17_Argentina_Cordoba_Rio-Segundo_EDA (writer SHAPEFILE_1)
    BOUNDING_BOX -> Clipper_14 [CLIPPER]
    BOUNDING_BOX -> Clipper [CANDIDATE]
Europe-REF_24_2022_Temperate_Broadleaf_Mixed_Forests (reader OGCGEOPACKAGE_1)
    attributes: cst_code text, date_part double, sfd_id mediumint, Ref_year int, fid int,PrimaryKey
    -> Reprojector_10
Reprojector_10
    DEST = EPSG:4326
    INTERPOLATION_TYPE_NAME = Nearest Neighbor
    RASTER_CELL_SIZE = Preserve Cells
    RASTER_TOLERANCE = 0.0
    REPROJECTED -> BoundingBoxAccumulator_37
BoundingBoxAccumulator_37
    ACCUM_ATTRS_NAME = Merge Incoming Attributes
    BOUNDING_BOX -> DL_fieldborders_ARG.6.17_Argentina_Cordoba_Rio-Segundo_EDA (writer SHAPEFILE_1)
    BOUNDING_BOX -> Clipper_17 [CLIPPER]
    BOUNDING_BOX -> Clipper [CANDIDATE]
Europe-REF_25_2022_Temperate_Broadleaf_Mixed_Forests (reader OGCGEOPACKAGE_1)
    attributes: cst_code text, date_part double, sfd_id mediumint, Ref_year int, fid int,PrimaryKey
    -> Reprojector_11
Reprojector_11
    DEST = EPSG:4326
    INTERPOLATION_TYPE_NAME = Nearest Neighbor
    RASTER_CELL_SIZE = Preserve Cells
    RASTER_TOLERANCE = 0.0
    REPROJECTED -> BoundingBoxAccumulator_38
BoundingBoxAccumulator_38
    ACCUM_ATTRS_NAME = Merge Incoming Attributes
    BOUNDING_BOX -> DL_fieldborders_ARG.6.17_Argentina_Cordoba_Rio-Segundo_EDA (writer SHAPEFILE_1)
    BOUNDING_BOX -> Clipper_18 [CLIPPER]
    BOUNDING_BOX -> Clipper [CANDIDATE]
Europe-REF_393_2022_Mediterranean_Forests_Woodlands_Scrub (reader OGCGEOPACKAGE_1)
    attributes: ASE_annota double, ESA_Class text(254), Area_Crop double, Sum_Area text(200), Crop_Perce text(200), Keep text(200), fid int,PrimaryKey
    -> Reprojector_12
Reprojector_12
    DEST = EPSG:4326
    INTERPOLATION_TYPE_NAME = Nearest Neighbor
    RASTER_CELL_SIZE = Preserve Cells
    RASTER_TOLERANCE = 0.0
    REPROJECTED -> BoundingBoxAccumulator_39
BoundingBoxAccumulator_39
    ACCUM_ATTRS_NAME = Merge Incoming Attributes
    BOUNDING_BOX -> DL_fieldborders_ARG.6.17_Argentina_Cordoba_Rio-Segundo_EDA (writer SHAPEFILE_1)
    BOUNDING_BOX -> Clipper_19 [CLIPPER]
    BOUNDING_BOX -> Clipper [CANDIDATE]
Europe-REF_598_2022_Mediterranean_Forests_Woodlands_Scrub (reader OGCGEOPACKAGE_1)
    attributes: ASE_annota double, ESA_Class text(254), Area_Crop double, Sum_Area text(200), Crop_Perce text(200), Keep text(200), cat int, fid int,PrimaryKey
    -> Reprojector_13
Reprojector_13
    DEST = EPSG:4326
    INTERPOLATION_TYPE_NAME = Nearest Neighbor
    RASTER_CELL_SIZE = Preserve Cells
    RASTER_TOLERANCE = 0.0
    REPROJECTED -> BoundingBoxAccumulator_40
BoundingBoxAccumulator_40
    ACCUM_ATTRS_NAME = Merge Incoming Attributes
    BOUNDING_BOX -> DL_fieldborders_ARG.6.17_Argentina_Cordoba_Rio-Segundo_EDA (writer SHAPEFILE_1)
    BOUNDING_BOX -> Clipper_24 [CLIPPER]
    BOUNDING_BOX -> Clipper [CANDIDATE]
Europe-REF_15042_2022_Flooded_Grasslands_Savannas (reader OGCGEOPACKAGE_1)
    attributes: ASE_annota double, ESA_Class text(254), Area_Crop double, Sum_Area text(200), Crop_Perce text(200), Keep text(200), fid int,PrimaryKey
    -> Reprojector_21
Reprojector_21
    DEST = EPSG:4326
    INTERPOLATION_TYPE_NAME = Nearest Neighbor
    RASTER_CELL_SIZE = Preserve Cells
    RASTER_TOLERANCE = 0.0
    REPROJECTED -> BoundingBoxAccumulator_9
BoundingBoxAccumulator_9
    ACCUM_ATTRS_NAME = Merge Incoming Attributes
    BOUNDING_BOX -> DL_fieldborders_ARG.6.17_Argentina_Cordoba_Rio-Segundo_EDA (writer SHAPEFILE_1)
    BOUNDING_BOX -> Clipper_28 [CLIPPER]
    BOUNDING_BOX -> Clipper [CANDIDATE]
Europe-REF_15315_2022_Temperate_Broadleaf_Mixed_Forests (reader OGCGEOPACKAGE_1)
    attributes: ASE_annota double, ESA_Class text(254), Area_Crop double, Sum_Area text(200), Crop_Perce text(200), Keep text(200), cat int, fid int,PrimaryKey
    -> Reprojector_22
Reprojector_22
    DEST = EPSG:4326
    INTERPOLATION_TYPE_NAME = Nearest Neighbor
    RASTER_CELL_SIZE = Preserve Cells
    RASTER_TOLERANCE = 0.0
    REPROJECTED -> BoundingBoxAccumulator_10
BoundingBoxAccumulator_10
    ACCUM_ATTRS_NAME = Merge Incoming Attributes
    BOUNDING_BOX -> DL_fieldborders_ARG.6.17_Argentina_Cordoba_Rio-Segundo_EDA (writer SHAPEFILE_1)
    BOUNDING_BOX -> Clipper_33 [CLIPPER]
    BOUNDING_BOX -> Clipper [CANDIDATE]
Europe-REF_8004_2022_Boreal_Forests_Taiga (reader OGCGEOPACKAGE_1)
    attributes: ASE_annota double, ESA_Class text(254), Area_Crop double, Sum_Area text(200), Crop_Perce text(200), Keep text(200), cat int, fid int,PrimaryKey
    -> Reprojector_18
Reprojector_18
    DEST = EPSG:4326
    INTERPOLATION_TYPE_NAME = Nearest Neighbor
    RASTER_CELL_SIZE = Preserve Cells
    RASTER_TOLERANCE = 0.0
    REPROJECTED -> BoundingBoxAccumulator_45
BoundingBoxAccumulator_45
    ACCUM_ATTRS_NAME = Merge Incoming Attributes
    BOUNDING_BOX -> DL_fieldborders_ARG.6.17_Argentina_Cordoba_Rio-Segundo_EDA (writer SHAPEFILE_1)
    BOUNDING_BOX -> Clipper_25 [CLIPPER]
    BOUNDING_BOX -> Clipper [CANDIDATE]
Europe-REF_11539_2022_Boreal_Forests_Taiga (reader OGCGEOPACKAGE_1)
    attributes: ASE_annota double, ESA_Class text(254), Area_Crop double, Sum_Area text(200), Crop_Perce text(200), Keep text(200), cat int, fid int,PrimaryKey
    -> Reprojector_19
Reprojector_19
    DEST = EPSG:4326
    INTERPOLATION_TYPE_NAME = Nearest Neighbor
    RASTER_CELL_SIZE = Preserve Cells
    RASTER_TOLERANCE = 0.0
    REPROJECTED -> BoundingBoxAccumulator_46
BoundingBoxAccumulator_46
    ACCUM_ATTRS_NAME = Merge Incoming Attributes
    BOUNDING_BOX -> DL_fieldborders_ARG.6.17_Argentina_Cordoba_Rio-Segundo_EDA (writer SHAPEFILE_1)
    BOUNDING_BOX -> Clipper_26 [CLIPPER]
    BOUNDING_BOX -> Clipper [CANDIDATE]
Europe-REF_15719_2022_Boreal_Forests_Taiga (reader OGCGEOPACKAGE_1)
    attributes: ASE_annota double, ESA_Class text(254), Area_Crop double, Sum_Area text(200), Crop_Perce text(200), Keep text(200), cat int, fid int,PrimaryKey
    -> Reprojector_23
Reprojector_23
    DEST = EPSG:4326
    INTERPOLATION_TYPE_NAME = Nearest Neighbor
    RASTER_CELL_SIZE = Preserve Cells
    RASTER_TOLERANCE = 0.0
    REPROJECTED -> BoundingBoxAccumulator_11
BoundingBoxAccumulator_11
    ACCUM_ATTRS_NAME = Merge Incoming Attributes
    BOUNDING_BOX -> DL_fieldborders_ARG.6.17_Argentina_Cordoba_Rio-Segundo_EDA (writer SHAPEFILE_1)
    BOUNDING_BOX -> Clipper_30 [CLIPPER]
    BOUNDING_BOX -> Clipper [CANDIDATE]
Europe-REF_23736_2022_Deserts_Xeric_Shrublands (reader OGCGEOPACKAGE_1)
    attributes: ASE_annota double, ESA_Class text(254), Area_Crop double, Sum_Area text(200), Crop_Perce text(200), Keep text(200), fid int,PrimaryKey
    -> Reprojector_27
Reprojector_27
    DEST = EPSG:4326
    INTERPOLATION_TYPE_NAME = Nearest Neighbor
    RASTER_CELL_SIZE = Preserve Cells
    RASTER_TOLERANCE = 0.0
    REPROJECTED -> BoundingBoxAccumulator_15
BoundingBoxAccumulator_15
    ACCUM_ATTRS_NAME = Merge Incoming Attributes
    BOUNDING_BOX -> DL_fieldborders_ARG.6.17_Argentina_Cordoba_Rio-Segundo_EDA (writer SHAPEFILE_1)
    BOUNDING_BOX -> Clipper_7 [CLIPPER]
    BOUNDING_BOX -> Clipper [CANDIDATE]
Europe-REF_25006_2022_Deserts_Xeric_Shrublands (reader OGCGEOPACKAGE_1)
    attributes: ASE_annota double, ESA_Class text(254), Area_Crop double, Sum_Area text(200), Crop_Perce text(200), Keep text(200), fid int,PrimaryKey
    -> Reprojector_28
Reprojector_28
    DEST = EPSG:4326
    INTERPOLATION_TYPE_NAME = Nearest Neighbor
    RASTER_CELL_SIZE = Preserve Cells
    RASTER_TOLERANCE = 0.0
    REPROJECTED -> BoundingBoxAccumulator_16
BoundingBoxAccumulator_16
    ACCUM_ATTRS_NAME = Merge Incoming Attributes
    BOUNDING_BOX -> DL_fieldborders_ARG.6.17_Argentina_Cordoba_Rio-Segundo_EDA (writer SHAPEFILE_1)
    BOUNDING_BOX -> Clipper_3 [CLIPPER]
    BOUNDING_BOX -> Clipper [CANDIDATE]
Europe-REF_34531_2022_Deserts_Xeric_Shrublands (reader OGCGEOPACKAGE_1)
    attributes: ASE_annota double, ESA_Class text(254), Area_Crop double, Sum_Area text(200), Crop_Perce text(200), Keep text(200), cat int, fid int,PrimaryKey
    -> Reprojector_30
Reprojector_30
    DEST = EPSG:4326
    INTERPOLATION_TYPE_NAME = Nearest Neighbor
    RASTER_CELL_SIZE = Preserve Cells
    RASTER_TOLERANCE = 0.0
    REPROJECTED -> BoundingBoxAccumulator_18
BoundingBoxAccumulator_18
    ACCUM_ATTRS_NAME = Merge Incoming Attributes
    BOUNDING_BOX -> DL_fieldborders_ARG.6.17_Argentina_Cordoba_Rio-Segundo_EDA (writer SHAPEFILE_1)
    BOUNDING_BOX -> Clipper_6 [CLIPPER]
    BOUNDING_BOX -> Clipper [CANDIDATE]
DL_fieldborders_ARG.6.17_Argentina_Cordoba_Rio-Segundo_EDA (writer SHAPEFILE_1)
    attributes: ASE_annota double, ESA_Class varchar(254), Area_Crop double, Sum_Area varchar(200), Crop_Perce varchar(200), Keep varchar(200), fid number(20,0), cat number(20,0), cst_code varchar(254), date_part double, sfd_id long, Ref_year number(20,0)
Albania_10_1_Shkoder_Malesi-e-Madhe_field-borders (reader OGCGEOPACKAGE_5) [off]
    attributes: Geosys_Id text(200), area double, perimeter double, Country text(32), Admin_L1 text(34), Admin_L2 text(34), AUID text(32), fid int,PrimaryKey
    -> Reprojector [off]
France_11_5_Occitanie_Gers_field-borders (reader OGCGEOPACKAGE_6)
    attributes: Geosys_Id text(200), area double, perimeter double, Country text(254), Admin_L1 text(200), Admin_L2 text(200), AUID text(254), fid int,PrimaryKey
    -> Reprojector
Reprojector
    DEST = EPSG:4326
    INTERPOLATION_TYPE_NAME = Nearest Neighbor
    RASTER_CELL_SIZE = Preserve Cells
    RASTER_TOLERANCE = 0.0
    REPROJECTED -> Junction
Junction
    -> Clipper_5 [CANDIDATE]
    -> Clipper_10 [CANDIDATE]
    -> Clipper_11 [CANDIDATE]
    -> Clipper_16 [CANDIDATE]
    -> Clipper_13 [CANDIDATE]
    -> Clipper_26 [CANDIDATE]
    -> Clipper_12 [CANDIDATE]
    -> Clipper_27 [CANDIDATE]
    -> Clipper_28 [CANDIDATE]
    -> Clipper_15 [CANDIDATE]
    -> Clipper_33 [CANDIDATE]
    -> Clipper_30 [CANDIDATE]
    -> Clipper_14 [CANDIDATE]
    -> Clipper_17 [CANDIDATE]
    -> Clipper_18 [CANDIDATE]
    -> Clipper_29 [CANDIDATE]
    -> Clipper_32 [CANDIDATE]
    -> Clipper_19 [CANDIDATE]
    -> Clipper_24 [CANDIDATE]
    -> Clipper_21 [CANDIDATE]
    -> Clipper_31 [CANDIDATE]
    -> Clipper_7 [CANDIDATE]
    -> Clipper_3 [CANDIDATE]
    -> Clipper_20 [CANDIDATE]
    -> Clipper_23 [CANDIDATE]
    -> Clipper_22 [CANDIDATE]
    -> Clipper_25 [CANDIDATE]
    -> Clipper_2 [CANDIDATE]
    -> Clipper_6 [CANDIDATE]
    -> Clipper_4 [CANDIDATE]
    -> Clipper_8 [CANDIDATE]
Clipper_5
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_1_2022_Temperate_Broadleaf_Mixed_Forests (writer SHAPEFILE_2)
Europe-REF_1_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_10
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_3_2022_Temperate_Broadleaf_Mixed_Forests (writer SHAPEFILE_2)
Europe-REF_3_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_11
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_4_2022_Temperate_Broadleaf_Mixed_Forests (writer SHAPEFILE_2)
Europe-REF_4_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_16
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_7_2022_Temperate_Broadleaf_Mixed_Forests (writer SHAPEFILE_2)
Europe-REF_7_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_13
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_12_2022_Temperate_Broadleaf_Mixed_Forests (writer SHAPEFILE_2)
Europe-REF_12_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_12
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_16_2022_Temperate_Broadleaf_Mixed_Forests (writer SHAPEFILE_2)
Europe-REF_16_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_15
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_21_2022_Temperate_Broadleaf_Mixed_Forests (writer SHAPEFILE_2)
Europe-REF_21_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_14
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_22_2022_Temperate_Broadleaf_Mixed_Forests (writer SHAPEFILE_2)
Europe-REF_22_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_17
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_24_2022_Temperate_Broadleaf_Mixed_Forests (writer SHAPEFILE_2)
Europe-REF_24_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_18
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_25_2022_Temperate_Broadleaf_Mixed_Forests (writer SHAPEFILE_2)
Europe-REF_25_2022_Temperate_Broadleaf_Mixed_Forests (writer SHAPEFILE_2)
    attributes: cst_code varchar(254), date_part double, sfd_id long, Ref_year number(20,0), fid number(20,0), Geosys_Id varchar(200), area double, perimeter double, Country varchar(32), Admin_L1 varchar(34), Admin_L2 varchar(34), AUID varchar(32), Q__clipped varchar(3)
Clipper_19
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_393_2022_Mediterranean_Forests_Woodlands_Scrub (writer SHAPEFILE_2)
Europe-REF_393_2022_Mediterranean_Forests_Woodlands_Scrub (writer SHAPEFILE_2)
    attributes: ASE_annota double, ESA_Class varchar(254), Area_Crop double, Sum_Area varchar(200), Crop_Perce varchar(200), Keep varchar(200), fid number(20,0), Geosys_Id varchar(200), area double, perimeter double, Country varchar(32), Admin_L1 varchar(34), Admin_L2 varchar(34), AUID varchar(32), Q__clipped varchar(3)
Clipper_24
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_598_2022_Mediterranean_Forests_Woodlands_Scrub (writer SHAPEFILE_2)
Europe-REF_598_2022_Mediterranean_Forests_Woodlands_Scrub (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_21
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_1048_2022_Mediterranean_Forests_Woodlands_Scrub (writer SHAPEFILE_2)
Europe-REF_1048_2022_Mediterranean_Forests_Woodlands_Scrub (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_20
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_2018_2022_Mediterranean_Forests_Woodlands_Scrub (writer SHAPEFILE_2)
Europe-REF_2018_2022_Mediterranean_Forests_Woodlands_Scrub (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_23
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_5470_2022_Mediterranean_Forests_Woodlands_Scrub (writer SHAPEFILE_2)
Europe-REF_5470_2022_Mediterranean_Forests_Woodlands_Scrub (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_22
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_7474_2022_Mediterranean_Forests_Woodlands_Scrub (writer SHAPEFILE_2)
Europe-REF_7474_2022_Mediterranean_Forests_Woodlands_Scrub (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_25
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_8004_2022_Boreal_Forests_Taiga (writer SHAPEFILE_2)
Europe-REF_8004_2022_Boreal_Forests_Taiga (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_26
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_11539_2022_Boreal_Forests_Taiga (writer SHAPEFILE_2)
Europe-REF_11539_2022_Boreal_Forests_Taiga (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_27
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_11639_2022_Mediterranean_Forests_Woodlands_Scrub (writer SHAPEFILE_2)
Europe-REF_11639_2022_Mediterranean_Forests_Woodlands_Scrub (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_28
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_15042_2022_Flooded_Grasslands_Savannas (writer SHAPEFILE_2)
Europe-REF_15042_2022_Flooded_Grasslands_Savannas (writer SHAPEFILE_2)
    attributes: ASE_annota double, ESA_Class varchar(254), Area_Crop double, Sum_Area varchar(200), Crop_Perce varchar(200), Keep varchar(200), fid number(20,0), Geosys_Id varchar(200), area double, perimeter double, Country varchar(32), Admin_L1 varchar(34), Admin_L2 varchar(34), AUID varchar(32), Q__clipped varchar(3)
Clipper_33
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_15315_2022_Temperate_Broadleaf_Mixed_Forests (writer SHAPEFILE_2)
Europe-REF_15315_2022_Temperate_Broadleaf_Mixed_Forests (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_30
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_15719_2022_Boreal_Forests_Taiga (writer SHAPEFILE_2)
Europe-REF_15719_2022_Boreal_Forests_Taiga (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_29
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_18757_2022_Temperate_Grasslands_Savannas_Shrublands (writer SHAPEFILE_2)
Europe-REF_18757_2022_Temperate_Grasslands_Savannas_Shrublands (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_32
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_21540_2022_Temperate_Grasslands_Savannas_Shrublands (writer SHAPEFILE_2)
Europe-REF_21540_2022_Temperate_Grasslands_Savannas_Shrublands (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_31
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_22993_2022_Temperate_Grasslands_Savannas_Shrublands (writer SHAPEFILE_2)
Europe-REF_22993_2022_Temperate_Grasslands_Savannas_Shrublands (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_7
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_23736_2022_Deserts_Xeric_Shrublands (writer SHAPEFILE_2)
Europe-REF_23736_2022_Deserts_Xeric_Shrublands (writer SHAPEFILE_2)
    attributes: ASE_annota double, ESA_Class varchar(254), Area_Crop double, Sum_Area varchar(200), Crop_Perce varchar(200), Keep varchar(200), fid number(20,0), Geosys_Id varchar(200), area double, perimeter double, Country varchar(32), Admin_L1 varchar(34), Admin_L2 varchar(34), AUID varchar(32), Q__clipped varchar(3)
Clipper_3
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_25006_2022_Deserts_Xeric_Shrublands (writer SHAPEFILE_2)
Europe-REF_25006_2022_Deserts_Xeric_Shrublands (writer SHAPEFILE_2)
    attributes: ASE_annota double, ESA_Class varchar(254), Area_Crop double, Sum_Area varchar(200), Crop_Perce varchar(200), Keep varchar(200), fid number(20,0), Geosys_Id varchar(200), area double, perimeter double, Country varchar(32), Admin_L1 varchar(34), Admin_L2 varchar(34), AUID varchar(32), Q__clipped varchar(3)
Clipper_2
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_32582_2022_Temperate_Grasslands_Savannas_Shrublands (writer SHAPEFILE_2)
Europe-REF_32582_2022_Temperate_Grasslands_Savannas_Shrublands (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_6
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_34531_2022_Deserts_Xeric_Shrublands (writer SHAPEFILE_2)
Europe-REF_34531_2022_Deserts_Xeric_Shrublands (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_4
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_42077_2022_Temperate_Grasslands_Savannas_Shrublands (writer SHAPEFILE_2)
Europe-REF_42077_2022_Temperate_Grasslands_Savannas_Shrublands (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
Clipper_8
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Europe-REF_44674_2022_Temperate_Grasslands_Savannas_Shrublands (writer SHAPEFILE_2)
Europe-REF_44674_2022_Temperate_Grasslands_Savannas_Shrublands (writer SHAPEFILE_2)
    attributes: ASE_annota double, ESA_Class varchar(254), Area_Crop double, Sum_Area varchar(200), Crop_Perce varchar(200), Keep varchar(200), cat number(20,0), fid number(20,0), Geosys_Id varchar(200), area double, perimeter double, Country varchar(32), Admin_L1 varchar(34), Admin_L2 varchar(34), AUID varchar(32), Q__clipped varchar(3)
gadm_410 (reader OGCGEOPACKAGE_4)
    attributes: UID int, GID_0 text(10), NAME_0 text(32), VARNAME_0 text(29), GID_1 text(10), NAME_1 text(34), VARNAME_1 text(82), NL_NAME_1 text(87), ISO_1 text(10), HASC_1 text(10), CC_1 text(10), TYPE_1 text(32), ENGTYPE_1 text(32), VALIDFR_1 text(15), GID_2 text(12), NAME_2 text(34), VARNAME_2 text(39), NL_NAME_2 text(75), HASC_2 text(15), CC_2 text(12), TYPE_2 text(34), ENGTYPE_2 text(32), VALIDFR_2 text(15), GID_3 text(15), NAME_3 text(38), VARNAME_3 text(44), NL_NAME_3 text(56), HASC_3 text(27), CC_3 text(10), TYPE_3 text(32),
      ENGTYPE_3 text(32), VALIDFR_3 text(10), GID_4 text(18), NAME_4 text(34), VARNAME_4 text(35), CC_4 text(12), TYPE_4 text(29), ENGTYPE_4 text(29), VALIDFR_4 text(10), GID_5 text(19), NAME_5 text(34), CC_5 text(10), TYPE_5 text(22), ENGTYPE_5 text(10), GOVERNEDBY text(17), SOVEREIGN text(32), DISPUTEDBY text(32), REGION text(32), VARREGION text(48), COUNTRY text(32), CONTINENT text(13), SUBCONT text(10), fid int,PrimaryKey
    -> Reprojector_33
Reprojector_33
    DEST = EPSG:4326
    INTERPOLATION_TYPE_NAME = Nearest Neighbor
    RASTER_CELL_SIZE = Preserve Cells
    RASTER_TOLERANCE = 0.0
    REPROJECTED -> AttributeManager
AttributeManager
    ATTR_TABLE:
      REMOVE UID
      REMOVE GID_0
      REMOVE VARNAME_0
      REMOVE GID_1
      REMOVE VARNAME_1
      REMOVE NL_NAME_1
      REMOVE ISO_1
      REMOVE HASC_1
      REMOVE CC_1
      REMOVE TYPE_1
      REMOVE ENGTYPE_1
      REMOVE VALIDFR_1
      REMOVE GID_2
      REMOVE VARNAME_2
      REMOVE NL_NAME_2
      REMOVE HASC_2
      REMOVE CC_2
      REMOVE TYPE_2
      REMOVE ENGTYPE_2
      REMOVE VALIDFR_2
      REMOVE GID_3
      REMOVE VARNAME_3
      REMOVE NL_NAME_3
      REMOVE HASC_3
      REMOVE CC_3
      REMOVE TYPE_3
      REMOVE ENGTYPE_3
      REMOVE VALIDFR_3
      REMOVE GID_4
      REMOVE NAME_4
      REMOVE VARNAME_4
      REMOVE CC_4
      REMOVE TYPE_4
      REMOVE ENGTYPE_4
      REMOVE VALIDFR_4
      REMOVE GID_5
      REMOVE NAME_5
      REMOVE CC_5
      REMOVE TYPE_5
      REMOVE ENGTYPE_5
      REMOVE GOVERNEDBY
      REMOVE SOVEREIGN
      REMOVE DISPUTEDBY
      REMOVE REGION
      REMOVE VARREGION
      REMOVE COUNTRY
      REMOVE CONTINENT
      REMOVE SUBCONT
      REMOVE fid
    -> Clipper [CLIPPER]
Clipper
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeManager_2
AttributeManager_2
    ATTR_TABLE:
      REMOVE NAME_0
      REMOVE NAME_1
      REMOVE NAME_3
      REMOVE ASE_annota
      REMOVE ESA_Class
      REMOVE Area_Crop
      REMOVE Sum_Area
      REMOVE Crop_Perce
      REMOVE Keep
      REMOVE fid
      REMOVE cat
      REMOVE cst_code
      REMOVE date_part
      REMOVE sfd_id
      REMOVE Ref_year
      REMOVE _clipped
    -> Clipper_Inside
Clipper_Inside: Inspector
