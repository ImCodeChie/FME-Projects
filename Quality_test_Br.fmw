FME workspace Quality_test_Br.fmw

Parameters:
- DestDataset_GEOTIFF = $(FME_MF_DIR)terrascope_download_20230920_110553\Cropped_Tile   # Destination GeoTIFF Folder
- SourceDataset_OGCGEOPACKAGE = ""$(FME_MF_DIR)Brazil_Reference\BZ-REF3117_3857.gpkg" "$(FME_MF_DIR)Brazil_Reference\BZ-REF6947_3857.gpkg" "$(FME_MF_DIR)Brazil_Reference\BZ-REF7087_3857.gpkg" "$(FME_MF_DIR)Brazil_Reference\BZ-REF8929_3857.gpkg" "$(FME_MF_DIR)Brazil_Reference\BZ-REF10011_3857.gpkg" "$(FME_MF_DIR)Brazil_Reference\BZ-REF11457_3857.gpkg" "$(FME_MF_DIR)Brazil_Reference\BZ-REF11670_3857.gpkg" "$(FME_MF_DIR)Brazil_Reference\BZ-REF11725_3857.gpkg" "$(FME_MF_DIR)Brazil_Reference\BZ-REF12813_3857.gpkg" "$(FME_MF_DIR)Brazil_Reference\BZ-REF13517_3857.gpkg" "$(FME_MF_DIR)Brazil_Reference\BZ-REF13895_3857.gpkg" "$(FME_MF_DIR)Brazil_Reference\BZ-REF14309_3857.gpkg" "$(FME_MF_DIR)Brazil_Reference\BZ-REF15524_3857.gpkg" "$(FME_MF_DIR)Brazil_Reference\BZ-REF15535_3857.gpkg" "$(FME_MF_DIR)Brazil_Reference\BZ-REF15796_3857.gpkg" "$(FME_MF_DIR)Brazil_Reference\BZ-REF16007_3857.gpkg" "$(FME_MF_DIR)Brazil_Reference\BZ-REF16583_3857.gpkg" "$(FME_MF_DIR)Brazil_Reference\BZ-REF16878_3857.gpkg" "$(FME_MF_DIR)Brazil_Reference\BZ-REF18423_3857.gpkg" "$(FME_MF_DIR)Brazil_Reference\BZ-REF19668_3857.gpkg""   # GeoPackage File
- SourceDataset_OGCGEOPACKAGE_5 = ""$(FME_MF_DIR)Brazil_Reference\**\BZ-REF3117_3857.gpkg" "$(FME_MF_DIR)Brazil_Reference\**\BZ-REF6947_3857.gpkg" "$(FME_MF_DIR)Brazil_Reference\**\BZ-REF7087_3857.gpkg" "$(FME_MF_DIR)Brazil_Reference\**\BZ-REF8929_3857.gpkg" "$(FME_MF_DIR)Brazil_Reference\**\BZ-REF10011_3857.gpkg" "$(FME_MF_DIR)Brazil_Reference\**\BZ-REF11457_3857.gpkg" "$(FME_MF_DIR)Brazil_Reference\**\BZ-REF11670_3857.gpkg" "$(FME_MF_DIR)Brazil_Reference\**\BZ-REF11725_3857.gpkg" "$(FME_MF_DIR)Brazil_Reference\**\BZ-REF12813_3857.gpkg" "$(FME_MF_DIR)Brazil_Reference\**\BZ-REF13517_3857.gpkg" "$(FME_MF_DIR)Brazil_Reference\**\BZ-REF13895_3857.gpkg" "$(FME_MF_DIR)Brazil_Reference\**\BZ-REF14309_3857.gpkg" "$(FME_MF_DIR)Brazil_Reference\**\BZ-REF15524_3857.gpkg" "$(FME_MF_DIR)Brazil_Reference\**\BZ-REF15535_3857.gpkg" "$(FME_MF_DIR)Brazil_Reference\**\BZ-REF15796_3857.gpkg" "$(FME_MF_DIR)Brazil_Reference\**\BZ-REF16007_3857.gpkg" "$(FME_MF_DIR)Brazil_Reference\**\BZ-REF16583_3857.gpkg" "$(FME_MF_DIR)Brazil_Reference\**\BZ-REF16878_3857.gpkg" "$(FME_MF_DIR)Brazil_Reference\**\BZ-REF18423_3857.gpkg" "$(FME_MF_DIR)Brazil_Reference\**\BZ-REF19668_3857.gpkg""   # GeoPackage File
- DestDataset_SHAPEFILE = F:\Quality_Test_ASE\Results\Europe   # Destination Esri Shapefile Folder
- DestDataset_OGCGEOPACKAGE_3 = F:\Quality_Test_ASE\Resized_Tiles\Europe   # GeoPackage File
- SourceDataset_GEOTIFF_2 = ""F:\Quality_Test_ASE\ESA_Masked\South_Africa\southafrica86_3857_std.tif" "F:\Quality_Test_ASE\ESA_Masked\South_Africa\southafrica183_3857_std00000000000000000000.tif" "F:\Quality_Test_ASE\ESA_Masked\South_Africa\southafrica856_3857_std00000000000000000000.tif" "F:\Quality_Test_ASE\ESA_Masked\South_Africa\southafrica910_3857_std00000000000000000000.tif""   # Source GeoTIFF File(s) or URL(s)
- DestDataset_OGCGEOPACKAGE_2 = F:\Quality_Test_ASE\Resized_Tiles\South_Africa   # GeoPackage File
- SourceDataset_OGCGEOPACKAGE_9 = F:\Quality_Test_ASE\Reference\Europe\Reference\deserts42077_3857_std00000000000000000000.gpkg   # GeoPackage File
- SourceDataset_OGCGEOPACKAGE_6 = F:\Quality_Test_ASE\Reference\Europe\Reference\taiga2_385700000000000000000000.gpkg   # GeoPackage File
- DestDataset_OGCGEOPACKAGE = F:\Quality_Test_ASE\Results\Europe   # GeoPackage File
- SourceDataset_GEOTIFF = ""F:\Quality_Test_ASE\ESA_Masked\Europe\deserts393_3857_std00000000000000000000.tif" "F:\Quality_Test_ASE\ESA_Masked\Europe\deserts15042_3857_std00000000000000000000.tif" "F:\Quality_Test_ASE\ESA_Masked\Europe\deserts23736_3857_std00000000000000000000.tif" "F:\Quality_Test_ASE\ESA_Masked\Europe\deserts25006_3857_std00000000000000000000.tif" "F:\Quality_Test_ASE\ESA_Masked\Europe\deserts34531_3857_std00000000000000000000.tif" "F:\Quality_Test_ASE\ESA_Masked\Europe\deserts42077_3857_std00000000000000000000.tif" "F:\Quality_Test_ASE\ESA_Masked\Europe\deserts44674_3857_std00000000000000000000.tif" "F:\Quality_Test_ASE\ESA_Masked\Europe\mediteranean598_3857_std00000000000000000000.tif" "F:\Quality_Test_ASE\ESA_Masked\Europe\mediteranean1048_3857_std00000000000000000000.tif" "F:\Quality_Test_ASE\ESA_Masked\Europe\mediteranean2018_3857_std00000000000000000000.tif" "F:\Quality_Test_ASE\ESA_Masked\Europe\mediteranean5470_3857_std00000000000000000000.tif" "F:\Quality_Test_ASE\ESA_Masked\Europe\mediteranean7474_3857_std00000000000000000000.tif" "F:\Quality_Test_ASE\ESA_Masked\Europe\mediteranean11639_3857_std00000000000000000000.tif" "F:\Quality_Test_ASE\ESA_Masked\Europe\taiga2_385700000000000000000000.tif" "F:\Quality_Test_ASE\ESA_Masked\Europe\taiga3_385700000000000000000000.tif" "F:\Quality_Test_ASE\ESA_Masked\Europe\taiga4_385700000000000000000000.tif" "F:\Quality_Test_ASE\ESA_Masked\Europe\temperate15315_3857_std00000000000000000000.tif" "F:\Quality_Test_ASE\ESA_Masked\Europe\temperate18757_3857_std00000000000000000000.tif" "F:\Quality_Test_ASE\ESA_Masked\Europe\temperate21540_3857_std00000000000000000000.tif" "F:\Quality_Test_ASE\ESA_Masked\Europe\temperate22993_3857_std00000000000000000000.tif" "F:\Quality_Test_ASE\ESA_Masked\Europe\temperate32582_3857_std00000000000000000000.tif""   # Source GeoTIFF File(s) or URL(s)

Readers:
- OGCGEOPACKAGE_1: OGCGEOPACKAGE from $(SourceDataset_OGCGEOPACKAGE)
- OGCGEOPACKAGE_2: OGCGEOPACKAGE from $(SourceDataset_OGCGEOPACKAGE_5)
- GEOTIFF_3: GEOTIFF from $(SourceDataset_GEOTIFF_2)
- OGCGEOPACKAGE_3: OGCGEOPACKAGE from $(SourceDataset_OGCGEOPACKAGE_9)
- OGCGEOPACKAGE_4: OGCGEOPACKAGE from $(SourceDataset_OGCGEOPACKAGE_6)
- GEOTIFF_1: GEOTIFF from $(SourceDataset_GEOTIFF)

Writers:
- GEOTIFF_2: GEOTIFF to $(DestDataset_GEOTIFF)
- SHAPEFILE_2: SHAPEFILE to $(DestDataset_SHAPEFILE)
- OGCGEOPACKAGE_6: OGCGEOPACKAGE to $(DestDataset_OGCGEOPACKAGE_3)
- OGCGEOPACKAGE_5: OGCGEOPACKAGE to $(DestDataset_OGCGEOPACKAGE_2)
- OGCGEOPACKAGE_7: OGCGEOPACKAGE to $(DestDataset_OGCGEOPACKAGE)

deserts15042_3857_std00000000000000000000 (reader OGCGEOPACKAGE_3) [off]
    attributes: id int, fid int,PrimaryKey
    -> Reprojector_4
Reprojector_4
    DEST = EPSG:3857
    INTERPOLATION_TYPE_NAME = Nearest Neighbor
    RASTER_CELL_SIZE = Preserve Cells
    RASTER_TOLERANCE = 0.0
    REPROJECTED -> Junction_5
Junction_5
    -> BoundingBoxAccumulator_2
    -> AttributeCreator
BoundingBoxAccumulator_2
    ACCUM_ATTRS_NAME = Use Attributes From One Feature
    BOUNDING_BOX -> Junction_8
Junction_8
    -> southafrica910_3857_std0000000000000000000000 (writer OGCGEOPACKAGE_6)
    -> Clipper [CLIPPER]
southafrica910_3857_std0000000000000000000000 (writer OGCGEOPACKAGE_6) [off]
    attributes: id int, fid int,PrimaryKey
deserts23736_3857_std00000000000000000000 (reader OGCGEOPACKAGE_3) [off]
    attributes: id int, fid int,PrimaryKey
    -> Reprojector_5
Reprojector_5
    DEST = EPSG:3857
    INTERPOLATION_TYPE_NAME = Nearest Neighbor
    RASTER_CELL_SIZE = Preserve Cells
    RASTER_TOLERANCE = 0.0
    REPROJECTED -> Junction_6
Junction_6
    -> BoundingBoxAccumulator_3
    -> AttributeCreator
BoundingBoxAccumulator_3
    ACCUM_ATTRS_NAME = Use Attributes From One Feature
    BOUNDING_BOX -> Junction_9
Junction_9
    -> Clipper [CLIPPER]
    -> southafrica910_3857_std0000000000000000000001 (writer OGCGEOPACKAGE_6)
southafrica910_3857_std0000000000000000000001 (writer OGCGEOPACKAGE_6) [off]
    attributes: id int, fid int,PrimaryKey
deserts25006_3857_std00000000000000000000 (reader OGCGEOPACKAGE_3) [off]
    attributes: id int, fid int,PrimaryKey
    -> Reprojector_6
Reprojector_6
    DEST = EPSG:3857
    INTERPOLATION_TYPE_NAME = Nearest Neighbor
    RASTER_CELL_SIZE = Preserve Cells
    RASTER_TOLERANCE = 0.0
    REPROJECTED -> Junction_7
Junction_7
    -> BoundingBoxAccumulator_4
    -> AttributeCreator
BoundingBoxAccumulator_4
    ACCUM_ATTRS_NAME = Use Attributes From One Feature
    BOUNDING_BOX -> Junction_10
Junction_10
    -> southafrica910_3857_std0000000000000000000002 (writer OGCGEOPACKAGE_6)
    -> Clipper [CLIPPER]
southafrica910_3857_std0000000000000000000002 (writer OGCGEOPACKAGE_6) [off]
    attributes: id int, fid int,PrimaryKey
deserts34531_3857_std00000000000000000000 (reader OGCGEOPACKAGE_3) [off]
    attributes: id int, fid int,PrimaryKey
    -> Reprojector_7
Reprojector_7
    DEST = EPSG:3857
    INTERPOLATION_TYPE_NAME = Nearest Neighbor
    RASTER_CELL_SIZE = Preserve Cells
    RASTER_TOLERANCE = 0.0
    REPROJECTED -> Junction_11
Junction_11
    -> BoundingBoxAccumulator_5
    -> AttributeCreator
BoundingBoxAccumulator_5
    ACCUM_ATTRS_NAME = Use Attributes From One Feature
    BOUNDING_BOX -> Junction_12
Junction_12
    -> Clipper [CLIPPER]
    -> southafrica910_3857_std0000000000000000000003 (writer OGCGEOPACKAGE_6)
southafrica910_3857_std0000000000000000000003 (writer OGCGEOPACKAGE_6) [off]
    attributes: id int, fid int,PrimaryKey
deserts42077_3857_std00000000000000000000 (reader OGCGEOPACKAGE_3)
    attributes: id int, fid int,PrimaryKey
    -> Reprojector_8
Reprojector_8
    DEST = EPSG:3857
    INTERPOLATION_TYPE_NAME = Nearest Neighbor
    RASTER_CELL_SIZE = Preserve Cells
    RASTER_TOLERANCE = 0.0
    REPROJECTED -> Junction_13
Junction_13
    -> BoundingBoxAccumulator_6
    -> AttributeCreator
BoundingBoxAccumulator_6
    ACCUM_ATTRS_NAME = Use Attributes From One Feature
    BOUNDING_BOX -> Junction_14
Junction_14
    -> Clipper [CLIPPER]
    -> southafrica910_3857_std000000000000000000000000 (writer OGCGEOPACKAGE_6)
southafrica910_3857_std000000000000000000000000 (writer OGCGEOPACKAGE_6) [off]
    attributes: id int, fid int,PrimaryKey
deserts44674_3857_std00000000000000000000 (reader OGCGEOPACKAGE_3) [off]
    attributes: id int, fid int,PrimaryKey
    -> Reprojector_9
Reprojector_9
    DEST = EPSG:3857
    INTERPOLATION_TYPE_NAME = Nearest Neighbor
    RASTER_CELL_SIZE = Preserve Cells
    RASTER_TOLERANCE = 0.0
    REPROJECTED -> Junction_15
Junction_15
    -> BoundingBoxAccumulator_7
    -> AttributeCreator
BoundingBoxAccumulator_7
    ACCUM_ATTRS_NAME = Use Attributes From One Feature
    BOUNDING_BOX -> Junction_16
Junction_16
    -> Clipper [CLIPPER]
    -> southafrica910_3857_std000000000000000000000100 (writer OGCGEOPACKAGE_6)
southafrica910_3857_std000000000000000000000100 (writer OGCGEOPACKAGE_6) [off]
    attributes: id int, fid int,PrimaryKey
mediteranean598_3857_std00000000000000000000 (reader OGCGEOPACKAGE_3) [off]
    attributes: id int, fid int,PrimaryKey
    -> Reprojector_10
Reprojector_10
    DEST = EPSG:3857
    INTERPOLATION_TYPE_NAME = Nearest Neighbor
    RASTER_CELL_SIZE = Preserve Cells
    RASTER_TOLERANCE = 0.0
    REPROJECTED -> Junction_17
Junction_17
    -> BoundingBoxAccumulator_8
    -> AttributeCreator
BoundingBoxAccumulator_8
    ACCUM_ATTRS_NAME = Use Attributes From One Feature
    BOUNDING_BOX -> Junction_18
Junction_18
    -> Clipper [CLIPPER]
    -> southafrica910_3857_std000000000000000000000200 (writer OGCGEOPACKAGE_6)
southafrica910_3857_std000000000000000000000200 (writer OGCGEOPACKAGE_6) [off]
    attributes: id int, fid int,PrimaryKey
mediteranean1048_3857_std00000000000000000000 (reader OGCGEOPACKAGE_3) [off]
    attributes: id int, fid int,PrimaryKey
    -> Reprojector_11
Reprojector_11
    DEST = EPSG:3857
    INTERPOLATION_TYPE_NAME = Nearest Neighbor
    RASTER_CELL_SIZE = Preserve Cells
    RASTER_TOLERANCE = 0.0
    REPROJECTED -> Junction_19
Junction_19
    -> BoundingBoxAccumulator_9
    -> AttributeCreator
BoundingBoxAccumulator_9
    ACCUM_ATTRS_NAME = Use Attributes From One Feature
    BOUNDING_BOX -> Junction_20
Junction_20
    -> Clipper [CLIPPER]
    -> southafrica910_3857_std0000000000000000000004 (writer OGCGEOPACKAGE_6)
southafrica910_3857_std0000000000000000000004 (writer OGCGEOPACKAGE_6) [off]
    attributes: id int, fid int,PrimaryKey
mediteranean2018_3857_std00000000000000000000 (reader OGCGEOPACKAGE_3) [off]
    attributes: id int, fid int,PrimaryKey
    -> Reprojector_12
Reprojector_12
    DEST = EPSG:3857
    INTERPOLATION_TYPE_NAME = Nearest Neighbor
    RASTER_CELL_SIZE = Preserve Cells
    RASTER_TOLERANCE = 0.0
    REPROJECTED -> Junction_21
Junction_21
    -> BoundingBoxAccumulator_10
    -> AttributeCreator
BoundingBoxAccumulator_10
    ACCUM_ATTRS_NAME = Use Attributes From One Feature
    BOUNDING_BOX -> Junction_22
Junction_22
    -> Clipper [CLIPPER]
    -> southafrica910_3857_std000000000000000000000001 (writer OGCGEOPACKAGE_6)
southafrica910_3857_std000000000000000000000001 (writer OGCGEOPACKAGE_6) [off]
    attributes: id int, fid int,PrimaryKey
mediteranean5470_3857_std00000000000000000000 (reader OGCGEOPACKAGE_3) [off]
    attributes: id int, fid int,PrimaryKey
    -> Reprojector_13
Reprojector_13
    DEST = EPSG:3857
    INTERPOLATION_TYPE_NAME = Nearest Neighbor
    RASTER_CELL_SIZE = Preserve Cells
    RASTER_TOLERANCE = 0.0
    REPROJECTED -> Junction_23
Junction_23
    -> BoundingBoxAccumulator_11
    -> AttributeCreator
BoundingBoxAccumulator_11
    ACCUM_ATTRS_NAME = Use Attributes From One Feature
    BOUNDING_BOX -> Junction_24
Junction_24
    -> Clipper [CLIPPER]
    -> southafrica910_3857_std000000000000000000000101 (writer OGCGEOPACKAGE_6)
southafrica910_3857_std000000000000000000000101 (writer OGCGEOPACKAGE_6) [off]
    attributes: id int, fid int,PrimaryKey
mediteranean7474_3857_std00000000000000000000 (reader OGCGEOPACKAGE_3) [off]
    attributes: id int, fid int,PrimaryKey
    -> Reprojector_14
Reprojector_14
    DEST = EPSG:3857
    INTERPOLATION_TYPE_NAME = Nearest Neighbor
    RASTER_CELL_SIZE = Preserve Cells
    RASTER_TOLERANCE = 0.0
    REPROJECTED -> Junction_25
Junction_25
    -> BoundingBoxAccumulator_12
    -> AttributeCreator
BoundingBoxAccumulator_12
    ACCUM_ATTRS_NAME = Use Attributes From One Feature
    BOUNDING_BOX -> Junction_26
Junction_26
    -> Clipper [CLIPPER]
    -> southafrica910_3857_std000000000000000000000201 (writer OGCGEOPACKAGE_6)
southafrica910_3857_std000000000000000000000201 (writer OGCGEOPACKAGE_6) [off]
    attributes: id int, fid int,PrimaryKey
mediteranean11639_3857_std00000000000000000000 (reader OGCGEOPACKAGE_3) [off]
    attributes: id int, fid int,PrimaryKey
    -> Reprojector_15
Reprojector_15
    DEST = EPSG:3857
    INTERPOLATION_TYPE_NAME = Nearest Neighbor
    RASTER_CELL_SIZE = Preserve Cells
    RASTER_TOLERANCE = 0.0
    REPROJECTED -> Junction_27
Junction_27
    -> BoundingBoxAccumulator_13
    -> AttributeCreator
BoundingBoxAccumulator_13
    ACCUM_ATTRS_NAME = Use Attributes From One Feature
    BOUNDING_BOX -> Junction_28
Junction_28
    -> Clipper [CLIPPER]
    -> southafrica910_3857_std000000000000000000000300 (writer OGCGEOPACKAGE_6)
southafrica910_3857_std000000000000000000000300 (writer OGCGEOPACKAGE_6) [off]
    attributes: id int, fid int,PrimaryKey
temperate15315_3857_std00000000000000000000 (reader OGCGEOPACKAGE_3) [off]
    attributes: id int, fid int,PrimaryKey
    -> Reprojector_19
Reprojector_19
    DEST = EPSG:3857
    INTERPOLATION_TYPE_NAME = Nearest Neighbor
    RASTER_CELL_SIZE = Preserve Cells
    RASTER_TOLERANCE = 0.0
    REPROJECTED -> Junction_35
Junction_35
    -> BoundingBoxAccumulator_17
    -> AttributeCreator
BoundingBoxAccumulator_17
    ACCUM_ATTRS_NAME = Use Attributes From One Feature
    BOUNDING_BOX -> Junction_36
Junction_36
    -> Clipper [CLIPPER]
    -> southafrica910_3857_std0000000000000000000005 (writer OGCGEOPACKAGE_6)
southafrica910_3857_std0000000000000000000005 (writer OGCGEOPACKAGE_6) [off]
    attributes: id int, fid int,PrimaryKey
temperate18757_3857_std00000000000000000000 (reader OGCGEOPACKAGE_3) [off]
    attributes: id int, fid int,PrimaryKey
    -> Reprojector_20
Reprojector_20
    DEST = EPSG:3857
    INTERPOLATION_TYPE_NAME = Nearest Neighbor
    RASTER_CELL_SIZE = Preserve Cells
    RASTER_TOLERANCE = 0.0
    REPROJECTED -> Junction_37
Junction_37
    -> BoundingBoxAccumulator_18
    -> AttributeCreator
BoundingBoxAccumulator_18
    ACCUM_ATTRS_NAME = Use Attributes From One Feature
    BOUNDING_BOX -> Junction_38
Junction_38
    -> Clipper [CLIPPER]
    -> southafrica910_3857_std000000000000000000000002 (writer OGCGEOPACKAGE_6)
southafrica910_3857_std000000000000000000000002 (writer OGCGEOPACKAGE_6) [off]
    attributes: id int, fid int,PrimaryKey
temperate21540_3857_std00000000000000000000 (reader OGCGEOPACKAGE_3) [off]
    attributes: id int, fid int,PrimaryKey
    -> Reprojector_21
Reprojector_21
    DEST = EPSG:3857
    INTERPOLATION_TYPE_NAME = Nearest Neighbor
    RASTER_CELL_SIZE = Preserve Cells
    RASTER_TOLERANCE = 0.0
    REPROJECTED -> Junction_39
Junction_39
    -> BoundingBoxAccumulator_19
    -> AttributeCreator
BoundingBoxAccumulator_19
    ACCUM_ATTRS_NAME = Use Attributes From One Feature
    BOUNDING_BOX -> Junction_40
Junction_40
    -> Clipper [CLIPPER]
    -> southafrica910_3857_std000000000000000000000102 (writer OGCGEOPACKAGE_6)
southafrica910_3857_std000000000000000000000102 (writer OGCGEOPACKAGE_6) [off]
    attributes: id int, fid int,PrimaryKey
temperate22993_3857_std00000000000000000000 (reader OGCGEOPACKAGE_3) [off]
    attributes: id int, fid int,PrimaryKey
    -> Reprojector_22
Reprojector_22
    DEST = EPSG:3857
    INTERPOLATION_TYPE_NAME = Nearest Neighbor
    RASTER_CELL_SIZE = Preserve Cells
    RASTER_TOLERANCE = 0.0
    REPROJECTED -> Junction_41
Junction_41
    -> BoundingBoxAccumulator_20
    -> AttributeCreator
BoundingBoxAccumulator_20
    ACCUM_ATTRS_NAME = Use Attributes From One Feature
    BOUNDING_BOX -> Junction_42
Junction_42
    -> Clipper [CLIPPER]
    -> southafrica910_3857_std000000000000000000000202 (writer OGCGEOPACKAGE_6)
southafrica910_3857_std000000000000000000000202 (writer OGCGEOPACKAGE_6) [off]
    attributes: id int, fid int,PrimaryKey
temperate32582_3857_std00000000000000000000 (reader OGCGEOPACKAGE_3) [off]
    attributes: id int, fid int,PrimaryKey
    -> Reprojector_23
Reprojector_23
    DEST = EPSG:3857
    INTERPOLATION_TYPE_NAME = Nearest Neighbor
    RASTER_CELL_SIZE = Preserve Cells
    RASTER_TOLERANCE = 0.0
    REPROJECTED -> Junction_43
Junction_43
    -> BoundingBoxAccumulator_21
    -> AttributeCreator
BoundingBoxAccumulator_21
    ACCUM_ATTRS_NAME = Use Attributes From One Feature
    BOUNDING_BOX -> Junction_44
Junction_44
    -> Clipper [CLIPPER]
    -> southafrica910_3857_std000000000000000000000301 (writer OGCGEOPACKAGE_6)
southafrica910_3857_std000000000000000000000301 (writer OGCGEOPACKAGE_6) [off]
    attributes: id int, fid int,PrimaryKey
GEOTIFF (reader GEOTIFF_3) [off]
    -> Reprojector_2 [off]
GEOTIFF (reader GEOTIFF_1)
    -> Reprojector_2
Reprojector_2
    DEST = EPSG:3857
    INTERPOLATION_TYPE_NAME = Nearest Neighbor
    RASTER_CELL_SIZE = Preserve Cells
    RASTER_TOLERANCE = 0.0
    REPROJECTED -> Clipper [CANDIDATE]
deserts393_3857_std00000000000000000000 (reader OGCGEOPACKAGE_3) [off]
    attributes: id int, fid int,PrimaryKey
    -> Reprojector_3
Reprojector_3
    DEST = EPSG:3857
    INTERPOLATION_TYPE_NAME = Nearest Neighbor
    RASTER_CELL_SIZE = Preserve Cells
    RASTER_TOLERANCE = 0.0
    REPROJECTED -> Junction
Junction
    -> BoundingBoxAccumulator
    -> AttributeCreator
BoundingBoxAccumulator
    ACCUM_ATTRS_NAME = Use Attributes From One Feature
    BOUNDING_BOX -> Junction_4
Junction_4
    -> Clipper [CLIPPER]
    -> southafrica910_3857_std00000000000000000000 (writer OGCGEOPACKAGE_6)
southafrica910_3857_std00000000000000000000 (writer OGCGEOPACKAGE_6) [off]
    attributes: id int, fid int,PrimaryKey
taiga2_385700000000000000000000 (reader OGCGEOPACKAGE_4) [off]
    attributes: cat mediumint, id mediumint, fid int,PrimaryKey
    -> Reprojector_16
Reprojector_16
    DEST = EPSG:3857
    INTERPOLATION_TYPE_NAME = Nearest Neighbor
    RASTER_CELL_SIZE = Preserve Cells
    RASTER_TOLERANCE = 0.0
    REPROJECTED -> Junction_29
Junction_29
    -> BoundingBoxAccumulator_14
    -> AttributeCreator
BoundingBoxAccumulator_14
    ACCUM_ATTRS_NAME = Use Attributes From One Feature
    BOUNDING_BOX -> Junction_30
Junction_30
    -> Clipper [CLIPPER]
    -> southafrica910_3857_std00000000000000000000000000 (writer OGCGEOPACKAGE_6)
southafrica910_3857_std00000000000000000000000000 (writer OGCGEOPACKAGE_6) [off]
    attributes: cat mediumint, id mediumint, fid int,PrimaryKey
taiga3_385700000000000000000000 (reader OGCGEOPACKAGE_3) [off]
    attributes: id int, fid int,PrimaryKey
    -> Reprojector_17
Reprojector_17
    DEST = EPSG:3857
    INTERPOLATION_TYPE_NAME = Nearest Neighbor
    RASTER_CELL_SIZE = Preserve Cells
    RASTER_TOLERANCE = 0.0
    REPROJECTED -> Junction_31
Junction_31
    -> BoundingBoxAccumulator_15
    -> AttributeCreator
BoundingBoxAccumulator_15
    ACCUM_ATTRS_NAME = Use Attributes From One Feature
    BOUNDING_BOX -> Junction_32
Junction_32
    -> Clipper [CLIPPER]
    -> southafrica910_3857_std00000000000000000000010000 (writer OGCGEOPACKAGE_6)
southafrica910_3857_std00000000000000000000010000 (writer OGCGEOPACKAGE_6) [off]
    attributes: id int, fid int,PrimaryKey
taiga4_385700000000000000000000 (reader OGCGEOPACKAGE_3) [off]
    attributes: id int, fid int,PrimaryKey
    -> Reprojector_18
Reprojector_18
    DEST = EPSG:3857
    INTERPOLATION_TYPE_NAME = Nearest Neighbor
    RASTER_CELL_SIZE = Preserve Cells
    RASTER_TOLERANCE = 0.0
    REPROJECTED -> Junction_33
Junction_33
    -> BoundingBoxAccumulator_16
    -> AttributeCreator
AttributeCreator
    ATTR_TABLE = SET_TO ASE_annotation = @Value(fid)
    -> AreaOnAreaOverlayer [AREA]
BoundingBoxAccumulator_16
    ACCUM_ATTRS_NAME = Use Attributes From One Feature
    BOUNDING_BOX -> Junction_34
Junction_34
    -> Clipper [CLIPPER]
    -> southafrica910_3857_std00000000000000000000020000 (writer OGCGEOPACKAGE_6)
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Junction_3
Junction_3
    -> RasterToPolygonCoercer
    -> GEOTIFF (writer GEOTIFF_2) [off]
GEOTIFF (writer GEOTIFF_2) [off]
    attributes: product_grid char(255), copyright char(255), creation_time char(255), algorithm_version char(255), license char(255), product_tile char(255), title char(255), product_type char(255), reference char(255), time_start char(255), legend char(255), time_end char(255), product_version char(255), product_crs char(255)
RasterToPolygonCoercer
    EXTRACT_NODATA = No
    LABEL_ATTRIBUTE = _label
    PRESERVE_ATTRIBUTES = Yes
    POLYGONS -> Generalizer_2 [off]
    POLYGONS -> TestFilter
Generalizer_2
    ALG_TEXT = NURBfit (Smooth)
    DEGREE = 6
    PRESERVE = No
    PRESERVE_PATHS = No
    SEGMENT_LENGTH = 0
    -> TestFilter [off]
TestFilter
    DEFAULT_VALUE = <UNFILTERED>
    PASSED_TEST_GROUP_OUTPUT = FIRST
    TEST_LIST = "BOOL_OP,OR,COMPOSITE_TEST,""""""1"""""",TEST_CLAUSE,TEST @Value(_label) = 40",Crop,"BOOL_OP,OR,COMPOSITE_TEST,""""""1"""""",TEST_CLAUSE,TEST @Value(_label) != 40",Other
    Crop -> AreaOnAreaOverlayer [AREA]
AreaOnAreaOverlayer
    ACCUM_ATTRS_NAME = Merge Incoming Attributes
    CLEANING_TOLERANCE = Automatic
    CONNECT_Z_MODE = First Wins
    DEAGGREGATE_INPUT = Yes
    OVC_ATTR = _overlaps
    AREA -> AttributeManager
AttributeManager
    ATTR_TABLE = SET_TO Conflict = FME_CONDITIONAL:DEFAULT_VALUE'_FME_NO_OP_'BOOL_OP;AND;COMPOSITE_TEST;1 AND 2;TEST ASE_annotation ATTRIBUTE_HAS_A_VALUE _FME_BLANK_STRING_;TEST @Value(_label) = 40'ASE_ESA_Conflict'FME_NUM_CONDITIONS2___
    -> TestFilter_3
TestFilter_3
    DEFAULT_VALUE = <UNFILTERED>
    PASSED_TEST_GROUP_OUTPUT = FIRST
    TEST_LIST:
      "BOOL_OP,AND,COMPOSITE_TEST,""""""1 AND 2"""""",TEST_CLAUSE,TEST ASE_annotation ATTRIBUTE_HAS_A_VALUE ""
      TEST _label ATTRIBUTE_HAS_A_VALUE """,Both,"BOOL_OP,OR,COMPOSITE_TEST,""""""1"""""",TEST_CLAUSE,TEST ASE_annotation ATTRIBUTE_HAS_A_VALUE """,ASE,"BOOL_OP,OR,COMPOSITE_TEST,""""""1"""""",TEST_CLAUSE,TEST _label ATTRIBUTE_HAS_A_VALUE """,ESA
    Both -> Aggregator_2
    ASE -> Aggregator_3
    ESA -> AreaCalculator
Aggregator_2
    ACCUM_ATTRS_NAME = Merge Incoming Attributes
    AGGREGATE_TYPE = Homogeneous Collection (If Possible)
    GROUP_BY = ASE_annotation
    MODE = Geometry - Assemble One Level
    SEP = ,
    AGGREGATE -> AreaCalculator_2
AreaCalculator_2
    AREA_ATTR = _area_Both
    AREA_TYPE = Plane Area
    MULT = 1
    -> AttributeManager_2
Aggregator_3
    ACCUM_ATTRS_NAME = Merge Incoming Attributes
    AGGREGATE_TYPE = Homogeneous Collection (If Possible)
    GROUP_BY = ASE_annotation
    MODE = Geometry - Assemble One Level
    SEP = ,
    AGGREGATE -> AreaCalculator_3
AreaCalculator_3
    AREA_ATTR = _area_ASE
    AREA_TYPE = Plane Area
    MULT = 1
    -> AttributeManager_2
AreaCalculator
    AREA_ATTR = _area_ESA
    AREA_TYPE = Plane Area
    MULT = 1
    -> AttributeManager_2
AttributeManager_2
    ATTR_TABLE:
      REMOVE _clipped
      REMOVE fid
      REMOVE id
      REMOVE _overlaps
    -> Aggregator
Aggregator
    ACCUM_ATTRS_NAME = Merge Incoming Attributes
    AGGREGATE_TYPE = Homogeneous Collection (If Possible)
    GROUP_BY = ASE_annotation
    MODE = Geometry - Assemble One Level
    SEP = ,
    AGGREGATE -> AttributeManager_3
AttributeManager_3
    ATTR_TABLE:
      SET_TO Sum_Area = @Evaluate(@sum(@Value(_area_ASE),@Value(_area_Both)))
      SET_TO Crop_Percentage = @Evaluate(100*@Value(_area_Both) / @Value(Sum_Area)
        )
    -> AttributeManager_4
AttributeManager_4
    ATTR_TABLE:
      RENAME_SET_VALUE _label > ESA_Class
      REMOVE Conflict
      RENAME_SET_VALUE _area_Both > Area_Crop
      REMOVE _area_ASE
      REMOVE _area_ESA
    -> TestFilter_2
TestFilter_2
    DEFAULT_VALUE = All other
    PASSED_TEST_GROUP_OUTPUT = FIRST
    TEST_LIST:
      "BOOL_OP,AND,COMPOSITE_TEST,""""""1 AND 2"""""",TEST_CLAUSE,TEST @Value(ESA_Class) = 40
      TEST ASE_annotation ATTRIBUTE_HAS_A_VALUE """,Keep
    Keep -> Dissolver_2
    All other -> Tester
Dissolver_2
    ACCUM_INPUT_ATTRS = Merge Incoming Attributes
    CLEANING_TOLERANCE = Automatic
    CONNECT_Z_MODE = First Wins
    DEAGGREGATE_INPUT = Yes
    GROUP_BY = ASE_annotation
    AREA -> DuplicateFilter
DuplicateFilter
    INPUT_ORDERED_CHOICE = No
    KEYATTR = ASE_annotation
    UNIQUE -> AttributeManager_5
AttributeManager_5
    ATTR_TABLE = SET_TO Keep = Yes
    -> Junction_2
Tester
    BOOL_OP = OR
    TEST_CLAUSE = TEST ASE_annotation ATTRIBUTE_HAS_A_VALUE ""
    TEST_MODE = TEST
    PASSED -> AttributeManager_6
AttributeManager_6
    -> Junction_2
Junction_2
    -> AttributeManager_7
AttributeManager_7
    ATTR_TABLE = SET_TO Keep = FME_CONDITIONAL:DEFAULT_VALUE'_FME_NO_OP_'BOOL_OP;OR;COMPOSITE_TEST;1;TEST @Value(Keep) != Yes'No'BOOL_OP;OR;COMPOSITE_TEST;1;TEST @Value(Crop_Percentage) <= 10'need to discuss'FME_NUM_CONDITIONS3___
    -> AttributeRounder
AttributeRounder
    PLACES = 1
    ROUND_TYPE = Nearest
    SRC_ATTRS = Crop_Percentage Area_Crop Sum_Area
    -> Brazil11_Result (writer SHAPEFILE_2)
    -> deserts393_3857_std00000000000000000000 (writer OGCGEOPACKAGE_7) [off]
deserts393_3857_std00000000000000000000 (writer OGCGEOPACKAGE_7) [off]
    attributes: ASE_annotation int,PrimaryKey, ESA_Class text, Area_Crop double, Sum_Area text(200), Crop_Percentage text(200), Keep text(200), cat mediumint
Brazil11_Result (writer SHAPEFILE_2)
    attributes: ASE_annota number(20,0), ESA_Class varchar(254), Area_Crop double, Sum_Area varchar(200), Crop_Perce varchar(200), Keep varchar(200), cat long
southafrica910_3857_std00000000000000000000020000 (writer OGCGEOPACKAGE_6) [off]
    attributes: id int, fid int,PrimaryKey
