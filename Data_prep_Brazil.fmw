FME workspace Data_prep_Brazil.fmw

Parameters:
- DestDataset_OGCGEOPACKAGE_2 = $(FME_MF_DIR)result\ML_outputs\Shapefile\ff.gpkg   # GeoPackage File
- DestDataset_SHAPEFILE_2 = $(FME_MF_DIR)result\ML_outputs\Shapefile   # Destination Esri Shapefile Folder
- SourceDataset_SHAPEFILE = ""$(FME_MF_DIR)FME_advanced\1\*.shp" "$(FME_MF_DIR)FME_advanced\2\*.shp" "$(FME_MF_DIR)FME_advanced\3\*.shp" "$(FME_MF_DIR)FME_advanced\4\*.shp" "$(FME_MF_DIR)FME_advanced\5\*.shp" "$(FME_MF_DIR)FME_advanced\7\*.shp" "$(FME_MF_DIR)FME_advanced\8\*.shp" "$(FME_MF_DIR)FME_advanced\10\*.shp" "$(FME_MF_DIR)FME_advanced\11\*.shp" "$(FME_MF_DIR)FME_advanced\13\*.shp" "$(FME_MF_DIR)FME_advanced\14\*.shp" "$(FME_MF_DIR)FME_advanced\16\*.shp" "$(FME_MF_DIR)FME_advanced\17\*.shp" "$(FME_MF_DIR)FME_advanced\18\*.shp" "$(FME_MF_DIR)FME_advanced\19\*.shp" "$(FME_MF_DIR)FME_advanced\20\*.shp""   # Source Esri Shapefile(s)
- FEATURE_TYPES_2 =
- SourceDataset_OGCGEOPACKAGE_7 = $(FME_MF_DIR)azure\Vectors\Reference\ASE\*.gpkg   # GeoPackage File
- DestDataset_SHAPEFILE_7 = $(FME_MF_DIR)result\ML_outputs\Shapefile   # Destination Esri Shapefile Folder

Readers:
- SHAPEFILE_2: SHAPEFILE from $(SourceDataset_SHAPEFILE)
- OGCGEOPACKAGE_4: OGCGEOPACKAGE from $(SourceDataset_OGCGEOPACKAGE_7)

Writers:
- OGCGEOPACKAGE_6: OGCGEOPACKAGE to $(DestDataset_OGCGEOPACKAGE_2)
- SHAPEFILE_3: SHAPEFILE to $(DestDataset_SHAPEFILE_2)
- SHAPEFILE_4: SHAPEFILE to $(DestDataset_SHAPEFILE_7)

brazil0_3857 (reader OGCGEOPACKAGE_4)
    attributes: id int, fid int,PrimaryKey
    -> GeometryValidator
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR
    SUMMARY = Detailed
    PASSED -> GeometryValidator_2
GeometryValidator_2
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> BoundingBoxAccumulator_7
BoundingBoxAccumulator_7
    ACCUM_ATTRS_NAME = Merge Incoming Attributes
    BOUNDING_BOX -> Clipper_7 [CLIPPER]
    BOUNDING_BOX -> DL_fieldborders_ARG.6.17_Argentina_Cordoba_Rio-Segundo_EDA (writer SHAPEFILE_3)
brazil1_3857 (reader OGCGEOPACKAGE_4)
    attributes: id int, fid int,PrimaryKey
    -> BoundingBoxAccumulator_8
BoundingBoxAccumulator_8
    ACCUM_ATTRS_NAME = Merge Incoming Attributes
    BOUNDING_BOX -> Clipper_8 [CLIPPER]
    BOUNDING_BOX -> DL_fieldborders_ARG.6.17_Argentina_Cordoba_Rio-Segundo_EDA (writer SHAPEFILE_3)
brazil2_3857 (reader OGCGEOPACKAGE_4)
    attributes: id int, fid int,PrimaryKey
    -> GeometryValidator_3
GeometryValidator_3
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> BoundingBoxAccumulator_9
BoundingBoxAccumulator_9
    ACCUM_ATTRS_NAME = Merge Incoming Attributes
    BOUNDING_BOX -> Clipper_9 [CLIPPER]
    BOUNDING_BOX -> DL_fieldborders_ARG.6.17_Argentina_Cordoba_Rio-Segundo_EDA (writer SHAPEFILE_3)
brazil3_3857 (reader OGCGEOPACKAGE_4)
    attributes: id int, fid int,PrimaryKey
    -> BoundingBoxAccumulator_10
BoundingBoxAccumulator_10
    ACCUM_ATTRS_NAME = Merge Incoming Attributes
    BOUNDING_BOX -> Clipper_11 [CLIPPER]
    BOUNDING_BOX -> DL_fieldborders_ARG.6.17_Argentina_Cordoba_Rio-Segundo_EDA (writer SHAPEFILE_3)
brazil4_3857 (reader OGCGEOPACKAGE_4)
    attributes: id int, fid int,PrimaryKey
    -> BoundingBoxAccumulator_11
BoundingBoxAccumulator_11
    ACCUM_ATTRS_NAME = Merge Incoming Attributes
    BOUNDING_BOX -> Clipper_12 [CLIPPER]
    BOUNDING_BOX -> DL_fieldborders_ARG.6.17_Argentina_Cordoba_Rio-Segundo_EDA (writer SHAPEFILE_3)
brazil5_3857 (reader OGCGEOPACKAGE_4)
    attributes: id int, fid int,PrimaryKey
    -> GeometryValidator_4
GeometryValidator_4
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> BoundingBoxAccumulator_12
BoundingBoxAccumulator_12
    ACCUM_ATTRS_NAME = Merge Incoming Attributes
    BOUNDING_BOX -> Clipper_10 [CLIPPER]
    BOUNDING_BOX -> DL_fieldborders_ARG.6.17_Argentina_Cordoba_Rio-Segundo_EDA (writer SHAPEFILE_3)
brazil6_3857 (reader OGCGEOPACKAGE_4)
    attributes: id int, fid int,PrimaryKey
    -> BoundingBoxAccumulator_13
BoundingBoxAccumulator_13
    ACCUM_ATTRS_NAME = Merge Incoming Attributes
    BOUNDING_BOX -> DL_fieldborders_ARG.6.17_Argentina_Cordoba_Rio-Segundo_EDA (writer SHAPEFILE_3)
    BOUNDING_BOX -> Clipper_19 [CLIPPER]
brazil7_3857 (reader OGCGEOPACKAGE_4)
    attributes: id int, fid int,PrimaryKey
    -> GeometryValidator_5
GeometryValidator_5
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> BoundingBoxAccumulator_14
BoundingBoxAccumulator_14
    ACCUM_ATTRS_NAME = Merge Incoming Attributes
    BOUNDING_BOX -> DL_fieldborders_ARG.6.17_Argentina_Cordoba_Rio-Segundo_EDA (writer SHAPEFILE_3)
    BOUNDING_BOX -> Clipper_20 [CLIPPER]
brazil8_3857 (reader OGCGEOPACKAGE_4)
    attributes: id int, fid int,PrimaryKey
    -> BoundingBoxAccumulator_15
BoundingBoxAccumulator_15
    ACCUM_ATTRS_NAME = Merge Incoming Attributes
    BOUNDING_BOX -> DL_fieldborders_ARG.6.17_Argentina_Cordoba_Rio-Segundo_EDA (writer SHAPEFILE_3)
    BOUNDING_BOX -> Clipper_21 [CLIPPER]
brazil10_3857 (reader OGCGEOPACKAGE_4)
    attributes: id int, fid int,PrimaryKey
    -> BoundingBoxAccumulator_16
BoundingBoxAccumulator_16
    ACCUM_ATTRS_NAME = Merge Incoming Attributes
    BOUNDING_BOX -> DL_fieldborders_ARG.6.17_Argentina_Cordoba_Rio-Segundo_EDA (writer SHAPEFILE_3)
    BOUNDING_BOX -> Clipper_24 [CLIPPER]
brazil11_3857 (reader OGCGEOPACKAGE_4)
    attributes: id int, fid int,PrimaryKey
    -> BoundingBoxAccumulator_17
BoundingBoxAccumulator_17
    ACCUM_ATTRS_NAME = Merge Incoming Attributes
    BOUNDING_BOX -> DL_fieldborders_ARG.6.17_Argentina_Cordoba_Rio-Segundo_EDA (writer SHAPEFILE_3)
    BOUNDING_BOX -> Clipper_22 [CLIPPER]
brazil12_3857 (reader OGCGEOPACKAGE_4)
    attributes: id int, fid int,PrimaryKey
    -> BoundingBoxAccumulator_18
BoundingBoxAccumulator_18
    ACCUM_ATTRS_NAME = Merge Incoming Attributes
    BOUNDING_BOX -> DL_fieldborders_ARG.6.17_Argentina_Cordoba_Rio-Segundo_EDA (writer SHAPEFILE_3)
    BOUNDING_BOX -> Clipper_13 [CLIPPER]
brazil13_3857 (reader OGCGEOPACKAGE_4)
    attributes: id int, fid int,PrimaryKey
    -> BoundingBoxAccumulator_19
BoundingBoxAccumulator_19
    ACCUM_ATTRS_NAME = Merge Incoming Attributes
    BOUNDING_BOX -> DL_fieldborders_ARG.6.17_Argentina_Cordoba_Rio-Segundo_EDA (writer SHAPEFILE_3)
    BOUNDING_BOX -> Clipper_14 [CLIPPER]
brazil14_3857 (reader OGCGEOPACKAGE_4)
    attributes: id int, fid int,PrimaryKey
    -> GeometryValidator_6
GeometryValidator_6
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> BoundingBoxAccumulator_20
BoundingBoxAccumulator_20
    ACCUM_ATTRS_NAME = Merge Incoming Attributes
    BOUNDING_BOX -> DL_fieldborders_ARG.6.17_Argentina_Cordoba_Rio-Segundo_EDA (writer SHAPEFILE_3)
    BOUNDING_BOX -> Clipper_15 [CLIPPER]
brazil15_3857 (reader OGCGEOPACKAGE_4)
    attributes: id int, fid int,PrimaryKey
    -> GeometryValidator_7
GeometryValidator_7
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> BoundingBoxAccumulator_21
BoundingBoxAccumulator_21
    ACCUM_ATTRS_NAME = Merge Incoming Attributes
    BOUNDING_BOX -> DL_fieldborders_ARG.6.17_Argentina_Cordoba_Rio-Segundo_EDA (writer SHAPEFILE_3)
    BOUNDING_BOX -> Clipper_17 [CLIPPER]
brazil16_3857 (reader OGCGEOPACKAGE_4)
    attributes: id int, fid int,PrimaryKey
    -> BoundingBoxAccumulator_22
BoundingBoxAccumulator_22
    ACCUM_ATTRS_NAME = Merge Incoming Attributes
    BOUNDING_BOX -> DL_fieldborders_ARG.6.17_Argentina_Cordoba_Rio-Segundo_EDA (writer SHAPEFILE_3)
    BOUNDING_BOX -> Clipper_18 [CLIPPER]
brazil17_3857 (reader OGCGEOPACKAGE_4)
    attributes: id int, fid int,PrimaryKey
    -> BoundingBoxAccumulator_23
BoundingBoxAccumulator_23
    ACCUM_ATTRS_NAME = Merge Incoming Attributes
    BOUNDING_BOX -> DL_fieldborders_ARG.6.17_Argentina_Cordoba_Rio-Segundo_EDA (writer SHAPEFILE_3)
    BOUNDING_BOX -> Clipper_16 [CLIPPER]
brazil18_3857 (reader OGCGEOPACKAGE_4)
    attributes: id int, fid int,PrimaryKey
    -> BoundingBoxAccumulator_24
BoundingBoxAccumulator_24
    ACCUM_ATTRS_NAME = Merge Incoming Attributes
    BOUNDING_BOX -> DL_fieldborders_ARG.6.17_Argentina_Cordoba_Rio-Segundo_EDA (writer SHAPEFILE_3)
    BOUNDING_BOX -> Clipper_23 [CLIPPER]
brazil19_3857 (reader OGCGEOPACKAGE_4)
    attributes: id int, fid int,PrimaryKey
    -> GeometryValidator_8
GeometryValidator_8
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR MISSING_VERTEX_NORMALS FME_CONTROLLER_QUERY_FILE]transformers/dependencies/geometryvalidator8/MISSING_VERTEX_NORMALS.fme]FME_CONTROLLER_CHOICE]MISSING_VERTEX_NORMALS CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> BoundingBoxAccumulator_25
BoundingBoxAccumulator_25
    ACCUM_ATTRS_NAME = Merge Incoming Attributes
    BOUNDING_BOX -> DL_fieldborders_ARG.6.17_Argentina_Cordoba_Rio-Segundo_EDA (writer SHAPEFILE_3)
    BOUNDING_BOX -> Clipper_25 [CLIPPER]
brazil20_3857 (reader OGCGEOPACKAGE_4)
    attributes: id int, fid int,PrimaryKey
    -> BoundingBoxAccumulator_26
BoundingBoxAccumulator_26
    ACCUM_ATTRS_NAME = Merge Incoming Attributes
    BOUNDING_BOX -> DL_fieldborders_ARG.6.17_Argentina_Cordoba_Rio-Segundo_EDA (writer SHAPEFILE_3)
    BOUNDING_BOX -> Clipper_26 [CLIPPER]
DL_fieldborders_ARG.6.17_Argentina_Cordoba_Rio-Segundo_EDA (writer SHAPEFILE_3)
    attributes: id number(20,0), fid number(20,0)
BRA.16.204_Brazil_Parana_Manoel-Ribas (reader SHAPEFILE_2)
    attributes: Geosys_Id varchar(200), area number(31,15), perimeter number(31,15), Country varchar(32), Admin_L1 varchar(34), Admin_L2 varchar(34), GID_2 varchar(32)
    -> Junction_2
Junction_2
    -> Clipper_7 [CANDIDATE]
    -> Clipper_8 [CANDIDATE]
    -> Clipper_9 [CANDIDATE]
    -> Clipper_11 [CANDIDATE]
    -> Clipper_12 [CANDIDATE]
    -> Clipper_10 [CANDIDATE]
    -> Clipper_19 [CANDIDATE]
    -> Clipper_20 [CANDIDATE]
    -> Clipper_21 [CANDIDATE]
    -> Clipper_23 [CANDIDATE]
    -> Clipper_16 [CANDIDATE]
    -> Clipper_18 [CANDIDATE]
    -> Clipper_17 [CANDIDATE]
    -> Clipper_15 [CANDIDATE]
    -> Clipper_14 [CANDIDATE]
    -> Clipper_13 [CANDIDATE]
    -> Clipper_22 [CANDIDATE]
    -> Clipper_24 [CANDIDATE]
    -> Clipper_25 [CANDIDATE]
    -> Clipper_26 [CANDIDATE]
Clipper_7
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-11457-20220901-20230630_FMEoutputs (writer SHAPEFILE_3)
BZ-11457-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_24
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-11670-20220901-20230630_FMEoutputs (writer SHAPEFILE_3)
BZ-11670-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_8
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-6947-20220901-20230630_FMEoutputs (writer SHAPEFILE_3)
BZ-6947-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_22
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-15524-20220901-20230630_FMEoutputs (writer SHAPEFILE_3)
BZ-15524-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_9
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-13570-20220901-20230630_FMEoutputs (writer SHAPEFILE_3)
BZ-13570-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_13
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-3117-20220901-20230630_FMEoutputs (writer SHAPEFILE_3)
BZ-3117-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_11
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-7087-20220901-20230630_FMEoutputs (writer SHAPEFILE_3)
BZ-7087-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_14
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-10011-20220901-20230630_FMEoutputs (writer SHAPEFILE_3)
BZ-10011-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_15
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-14309-20220901-20230630_FMEoutputs (writer SHAPEFILE_3)
BZ-14309-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_12
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-15535-20220901-20230630_FMEoutputs (writer SHAPEFILE_3)
BZ-15535-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_10
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-16583-20220901-20230630_FMEoutputs (writer SHAPEFILE_3)
BZ-16583-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_17
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-15796-20220901-20230630_FMEoutputs (writer SHAPEFILE_3)
BZ-15796-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_19
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-16878-20220901-20230630_FMEoutputs (writer SHAPEFILE_3)
BZ-16878-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_18
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-8929-20220901-20230630_FMEoutputs (writer SHAPEFILE_3)
BZ-8929-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_20
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-19668-20220901-20230630_FMEoutputs (writer SHAPEFILE_3)
BZ-19668-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_16
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-11725-20220901-20230630_FMEoutputs (writer SHAPEFILE_3)
BZ-11725-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_21
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-16007-20220901-20230630_FMEoutputs (writer SHAPEFILE_3)
BZ-16007-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_23
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-13895-20220901-20230630_FMEoutputs (writer SHAPEFILE_3)
BZ-13895-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_25
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-12813-20220901-20230630_FMEoutputs (writer SHAPEFILE_3)
BZ-12813-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
Clipper_26
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> BZ-18423-20220901-20230630_FMEoutputs (writer SHAPEFILE_3)
BZ-18423-20220901-20230630_FMEoutputs (writer SHAPEFILE_3)
    attributes: id number(20,0), fid number(20,0), Geosys_Id varchar(200), area number(31,15), perimeter number(31,15), Country varchar(32), Admin_L1 varchar(34), Admin_L2 varchar(34), GID_2 varchar(32), Q__clipped varchar(3)
