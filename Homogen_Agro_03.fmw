FME workspace Homogen_Agro_03.fmw

Parameters:
- DestDataset_SHAPEFILE =
- DestDataset_SHAPEFILE_2 =
- SourceDataset_GEOJSON =
- SourceDataset_GEOJSON_3 =
- SourceDataset_GEOTIFF =
- SourceDataset_GEOTIFF_3 =
- SourceDataset_OGCGEOPACKAGE =
- SourceDataset_OGCGEOPACKAGE_5 =
- SourceDataset_OGCGEOPACKAGE_6 =
- SourceDataset_OGCGEOPACKAGE_7 =
- SourceDataset_SHAPEFILE =
- SourceDataset_SHAPEFILE_12 =
- SourceDataset_SHAPEFILE_13 =
- SourceDataset_SHAPEFILE_7 =
- SourceDataset_SHAPEFILE_8 =

Readers:
- GEOTIFF_1: GEOTIFF from $(SourceDataset_GEOTIFF)
- SHAPEFILE_1: SHAPEFILE from $(SourceDataset_SHAPEFILE)
- SHAPEFILE_2: SHAPEFILE from $(SourceDataset_SHAPEFILE_7)
- SHAPEFILE_3: SHAPEFILE from $(SourceDataset_SHAPEFILE_13)
- SHAPEFILE_4: SHAPEFILE from $(SourceDataset_SHAPEFILE_8)
- SHAPEFILE_5: SHAPEFILE from $(SourceDataset_SHAPEFILE_12)
- GEOTIFF_2: GEOTIFF from $(SourceDataset_GEOTIFF_3)
- GEOJSON_1: GEOJSON from $(SourceDataset_GEOJSON)
- OGCGEOPACKAGE_1: OGCGEOPACKAGE from $(SourceDataset_OGCGEOPACKAGE_5)
- GEOJSON_2: GEOJSON from $(SourceDataset_GEOJSON_3)
- OGCGEOPACKAGE_2: OGCGEOPACKAGE from $(SourceDataset_OGCGEOPACKAGE)
- OGCGEOPACKAGE_3: OGCGEOPACKAGE from $(SourceDataset_OGCGEOPACKAGE_7)
- OGCGEOPACKAGE_4: OGCGEOPACKAGE from $(SourceDataset_OGCGEOPACKAGE_6)

Writers:
- SHAPEFILE_6: SHAPEFILE to $(DestDataset_SHAPEFILE)
- SHAPEFILE_7: SHAPEFILE to $(DestDataset_SHAPEFILE_2)

AttributeManager_3
    ATTR_TABLE:
      REMOVE osm_id
      REMOVE name
      REMOVE type
      REMOVE ID_RTE500
      REMOVE VOCATION
      REMOVE NB_CHAUSSE
      REMOVE NB_VOIES
      REMOVE ETAT
      REMOVE ACCES
      REMOVE RES_VERT
      REMOVE SENS
      REMOVE NUM_ROUTE
      REMOVE RES_EUROPE
      REMOVE LONGUEUR
      REMOVE full_id
      REMOVE osm_type
      REMOVE route
      REMOVE crossing:markings
      REMOVE name:zh
      REMOVE deck
      REMOVE payment:via_verde:lanes
      REMOVE railway:interlaced
      REMOVE ship
      REMOVE motorboat
      REMOVE canoe
      REMOVE boat
      REMOVE via_ferrata_scale
      REMOVE rungs
      REMOVE safety_rope
      REMOVE assisted_trail
      REMOVE bicycle:left
      REMOVE bicycle:forward
      REMOVE ref:refuges.info
      REMOVE departures_board
      REMOVE narrow
      REMOVE ref:2010
      REMOVE destination:ref:lanes:forward
      REMOVE destination:lanes:forward
      REMOVE razed:railway
      REMOVE overhang
      REMOVE ladder
      REMOVE minspeed:lanes:backward
      REMOVE parking:condition:left:residents
      REMOVE parking:lane:left:diagonal
      REMOVE material
      REMOVE bicycle:backward
      REMOVE cycleway:surface:colour
      REMOVE link
      REMOVE roller_coaster
      REMOVE leisure
      REMOVE attraction
      REMOVE maxspeed:source
      REMOVE lanes:both_ways
      REMOVE vehicle:lanes:forward
      REMOVE vehicle:lanes:backward
      REMOVE motorhome
      REMOVE parking:right:zone
      REMOVE parking:right:markings
      REMOVE parking:left:restriction
      REMOVE parking:left:reason
      REMOVE temporary:access
      REMOVE check_date
      REMOVE turn:backward
      REMOVE cycleway:lanes:backward
      REMOVE source:url
      REMOVE source:bus_bay
      REMOVE destination:symbol:forward
      REMOVE destination:ref:forward
      REMOVE maxspeed:lanes:backward
      REMOVE note:destination
      REMOVE source:name:ca
      REMOVE bus:lanes:forward
      REMOVE ref:kgs
      REMOVE source:bridge:name
      REMOVE maxweightrating
      REMOVE transit:lanes
      REMOVE source:destination:date
      REMOVE stroller
      REMOVE source:destination
      REMOVE turn:forward
      REMOVE placement:forward
      REMOVE surface:note
      REMOVE maxweight:forward:conditional
      REMOVE ramp
      REMOVE handrail
      REMOVE noexit
      REMOVE lanes:-2023
      REMOVE mtb:name
      REMOVE check_date:cycleway
      REMOVE placement:start
      REMOVE piste:name
      REMOVE maxspeed:hgv:lanes
      REMOVE sac_scale_ref
      REMOVE access:winter
      REMOVE sport
      REMOVE phone
      REMOVE border_type
      REMOVE cycleway:oneway
      REMOVE abandoned:highway
      REMOVE duration
      REMOVE path
      REMOVE maxspeed:recommended:forward
      REMOVE source:incline
      REMOVE name:de
      REMOVE footway
      REMOVE avalanche_protector:left
      REMOVE minspeed:lanes:forward
      REMOVE name:en
      REMOVE network:wikidata
      REMOVE maxspeed:caravan
      REMOVE destination:colour:backward
      REMOVE psv:lanes:forward
      REMOVE access:lanes:forward
      REMOVE parking:lane
      REMOVE name:wikipedia
      REMOVE arcade:right
      REMOVE cycleway:left:width
      REMOVE mtb:type
      REMOVE class:bicycle:mtb
      REMOVE parking:lane:left:capacity
      REMOVE man_made
      REMOVE 4wd_only
      REMOVE sidewalk:both:wheelchair
      REMOVE name:tr
      REMOVE name:ru
      REMOVE shelter
      REMOVE bin
      REMOVE bench
      REMOVE turn
      REMOVE mtb
      REMOVE historic:civilization
      REMOVE waterway
      REMOVE route_ref
      REMOVE public_transport
      REMOVE note:route_ref
      REMOVE tree_row
      REMOVE placement:backward
      REMOVE hiking
      REMOVE destination:ref:backward
      REMOVE comment
      REMOVE placement:both_ways
      REMOVE maxspeed:lanes:forward
      REMOVE historic
      REMOVE shoulder:left
      REMOVE description:es
      REMOVE maxheight:forward
      REMOVE oneway:hgv
      REMOVE abandoned
      REMOVE network
      REMOVE placement:end
      REMOVE cycleway:width
      REMOVE cycleway:buffer
      REMOVE was:lanes
      REMOVE traffic_sign:backward
      REMOVE horse_scale
      REMOVE sidewalk:right:bicycle
      REMOVE parking:condition:right:customers
      REMOVE side
      REMOVE overtaking:backward
      REMOVE bus_bay
      REMOVE bridge:name:oc
      REMOVE bridge:name:ca
      REMOVE priority
      REMOVE footway:right:wheelchair
      REMOVE footway:left:wheelchair
      REMOVE operator:wikipedia
      REMOVE operator:wikidata
      REMOVE circuits
      REMOVE cables
      REMOVE substation
      REMOVE ref:FR:RTE_nom
      REMOVE ref:FR:RTE
      REMOVE power
      REMOVE barrier
      REMOVE destination:colour:forward
      REMOVE cycleway:both:segregated
      REMOVE max
      REMOVE oneway:bus
      REMOVE tourism
      REMOVE mtb:scale:imba
      REMOVE source:imagery
      REMOVE motor_vehicle:lanes
      REMOVE piste:oneway
      REMOVE piste:difficulty
      REMOVE old_name:fr
      REMOVE lcn
      REMOVE ref:MMM
      REMOVE maxspeed:recommended:backward
      REMOVE lanes:bus:forward
      REMOVE source:width
      REMOVE recommended_speed
      REMOVE piste:type
      REMOVE piste:grooming
      REMOVE maxwidth
      REMOVE services
      REMOVE residents
      REMOVE int_name
      REMOVE source:name:br:date
      REMOVE speed
      REMOVE goods
      REMOVE source:bridge
      REMOVE alt_name:es
      REMOVE parking:lane:both:capacity
      REMOVE parking:condition:both:time_interval
      REMOVE parking:condition:both:maxstay
      REMOVE parking:condition:both:fee_per_hour
      REMOVE parking:condition:both:default
      REMOVE parking:condition:both:3:residents
      REMOVE parking:condition:both:3:maxstay
      REMOVE parking:condition:both:3
      REMOVE parking:condition:both:2:time_interval
      REMOVE parking:condition:both:2:maxstay
      REMOVE parking:condition:both:2:fee_per_hour
      REMOVE parking:condition:both:2
      REMOVE lanes:psv:backward
      REMOVE height
      REMOVE check_date:surface
      REMOVE proposed_ref
      REMOVE historic:start_date
      REMOVE historic:gauge
      REMOVE historic:end_date
      REMOVE historic:electrified
      REMOVE name:ja
      REMOVE bridge:name:nl
      REMOVE bridge:name:fr
      REMOVE bridge:name:en
      REMOVE maxwidth:physical
      REMOVE note:FR
      REMOVE construction
      REMOVE maxheight:lanes
      REMOVE smoothness:date
      REMOVE parking:right:fee
      REMOVE parking:right:orientation
      REMOVE motorhome:conditional
      REMOVE trailblazed
      REMOVE osmc:symbol
      REMOVE ford
      REMOVE cycleway:right:oneway
      REMOVE cycleway:lane
      REMOVE step_count
      REMOVE viaduct:name
      REMOVE bus:lanes:backward
      REMOVE access:lanes:backward
      REMOVE parking:lane:right:access
      REMOVE maxaxleload
      REMOVE psv:lanes:backward
      REMOVE source:cycleway
      REMOVE ref:MEL
      REMOVE brp_access
      REMOVE note:voltage
      REMOVE disused:railway
      REMOVE overtaking:goods
      REMOVE note:service
      REMOVE railway:preserved
      REMOVE trail_visibility
      REMOVE long_name
      REMOVE source:hazard
      REMOVE postal_code
      REMOVE minspeed:lanes
      REMOVE maxspeed:psv
      REMOVE hgv:lanes
      REMOVE cycleway:right:width
      REMOVE traffic_sign
      REMOVE source:heritage
      REMOVE ref:mhs
      REMOVE railway:scmt
      REMOVE railway:ptc
      REMOVE railway:etcs
      REMOVE railway:atb
      REMOVE mhs:inscription_date
      REMOVE heritage:operator
      REMOVE heritage
      REMOVE bridge:wikipedia
      REMOVE cycleway:right:segregated
      REMOVE location
      REMOVE cutting:right
      REMOVE animal_crossing
      REMOVE old:maxspeed
      REMOVE parking:lane:left:parallel
      REMOVE lanes:reversible
      REMOVE bridge:ref
      REMOVE mtb:scale:uphill
      REMOVE mtb:scale
      REMOVE bridge:movable
      REMOVE tactile_paving
      REMOVE segregated
      REMOVE footway:surface
      REMOVE cycleway:surface
      REMOVE crossing:island
      REMOVE crossing
      REMOVE motorcycle:conditional
      REMOVE motorcar:conditional
      REMOVE motor_vehicle:conditional
      REMOVE maxlength
      REMOVE abandoned:railway
      REMOVE inscription
      REMOVE ref:FFRP
      REMOVE sidewalk:left:bicycle
      REMOVE length
      REMOVE source:lanes
      REMOVE source:maxheight
      REMOVE shoulder:width
      REMOVE note:fr
      REMOVE hazard:animal
      REMOVE maxspeed:backward
      REMOVE old_name:eu
      REMOVE old_name:es
      REMOVE date
      REMOVE check_date:lit
      REMOVE sidewalk:bicycle
      REMOVE bridge:name:es
      REMOVE construction:railway:etcs
      REMOVE wikimedia_commons
      REMOVE maxspeed:advisory
      REMOVE tunnel:length
      REMOVE overtaking:forward
      REMOVE ele
      REMOVE change:lanes:forward
      REMOVE change:lanes:backward
      REMOVE noref
      REMOVE rcrc_ref
      REMOVE snowmobile
      REMOVE ski
      REMOVE maxspeed:forward
      REMOVE source:geometry
      REMOVE architect:wikidata
      REMOVE architect
      REMOVE local_ref
      REMOVE website
      REMOVE source:pkey
      REMOVE source:description
      REMOVE cycleway:left:oneway
      REMOVE destination:int_ref:lanes
      REMOVE highway:2021-11-05
      REMOVE access:2021-11-05
      REMOVE turn:bus:lanes:backward
      REMOVE lanes:bus:backward
      REMOVE hgv:forward
      REMOVE hgv:backward
      REMOVE hgv
      REMOVE alt_name:ca
      REMOVE source:highway
      REMOVE maxweight:conditional
      REMOVE traffic_calming
      REMOVE sidewalk:right:surface
      REMOVE sidewalk:left:surface
      REMOVE parking
      REMOVE psv:lanes
      REMOVE service
      REMOVE note:en
      REMOVE hgv:conditional
      REMOVE class:bicycle
      REMOVE signals
      REMOVE tunnel:name:es
      REMOVE tunnel:name:en
      REMOVE tunnel:name:ca
      REMOVE destination:nat_ref
      REMOVE ref:tunnel
      REMOVE mindistance:hgv
      REMOVE mindistance
      REMOVE overtaking:hgv
      REMOVE source:ref
      REMOVE source:name
      REMOVE destination:symbol:lanes
      REMOVE destination:colour:lanes
      REMOVE parking:condition:left
      REMOVE official_ref
      REMOVE motorcar
      REMOVE reg_ref
      REMOVE description
      REMOVE parking:both:zone
      REMOVE parking:both:markings
      REMOVE parking:both:fee
      REMOVE destination:forward
      REMOVE destination:backward
      REMOVE parking:both:reason
      REMOVE parking:right:restriction
      REMOVE parking:right
      REMOVE parking:left:zone
      REMOVE parking:left:orientation
      REMOVE parking:left:fee
      REMOVE parking:left
      REMOVE name:etymology:wikipedia
      REMOVE change:lanes
      REMOVE sidewalk:both:surface
      REMOVE taxi
      REMOVE psv
      REMOVE parking_lane
      REMOVE level
      REMOVE parking:both:restriction
      REMOVE destination:symbol:backward
      REMOVE destination:lanes:backward
      REMOVE zone:traffic
      REMOVE destination:ref:to:lanes
      REMOVE tracktype
      REMOVE bridge:structure
      REMOVE cycleway:left:lane
      REMOVE wheelchair
      REMOVE admin_level
      REMOVE destination:lang:es
      REMOVE width
      REMOVE maxweight
      REMOVE lanes:psv:forward
      REMOVE cs_dir:backward
      REMOVE oneway:psv
      REMOVE cycleway:right:lane
      REMOVE busway:left
      REMOVE ref:FR:SNCF_Reseau:GAIA
      REMOVE source:date
      REMOVE official_name
      REMOVE moped
      REMOVE mofa
      REMOVE access
      REMOVE toll:2021-08-31
      REMOVE name:ca
      REMOVE lanes:bus
      REMOVE maxweight:signed
      REMOVE source:lit
      REMOVE grande_circulation
      REMOVE parking:lane:right:parallel
      REMOVE parking:lane:right:capacity
      REMOVE parking:lane:right
      REMOVE parking:lane:left
      REMOVE parking:condition:right:time_interval
      REMOVE parking:condition:right:maxstay
      REMOVE parking:condition:right:fee_per_hour
      REMOVE parking:condition:right:default
      REMOVE parking:condition:right:3:residents
      REMOVE parking:condition:right:3:maxstay
      REMOVE parking:condition:right:3
      REMOVE parking:condition:right:2:time_interval
      REMOVE parking:condition:right:2:maxstay
      REMOVE parking:condition:right:2:fee_per_hour
      REMOVE parking:condition:right:2
      REMOVE parking:condition:right
      REMOVE oneway:bicycle
      REMOVE motor_vehicle:lanes:forward
      REMOVE incline
      REMOVE bicycle:lanes:forward
      REMOVE turn:lanes:backward
      REMOVE motor_vehicle:lanes:backward
      REMOVE cycleway:both:lane
      REMOVE bicycle:lanes:backward
      REMOVE railway:tvm
      REMOVE highspeed
      REMOVE overtaking
      REMOVE hazmat
      REMOVE destination:to
      REMOVE cutting
      REMOVE hazmat:E
      REMOVE maxspeed:lanes
      REMOVE trolley_wire
      REMOVE sidewalk:right
      REMOVE sidewalk:left
      REMOVE ref:colour_tx
      REMOVE name:eu
      REMOVE name:es
      REMOVE hazard
      REMOVE guard_rail
      REMOVE maxspeed:variable
      REMOVE parking:lane:both:parallel
      REMOVE destination:ref:to
      REMOVE covered
      REMOVE ref:colour
      REMOVE sidewalk:both
      REMOVE owner
      REMOVE ssvz
      REMOVE maxspeed:conditional
      REMOVE old_name
      REMOVE maxspeed:hgv:conditional
      REMOVE bridge:name
      REMOVE ref:FR:FANTOIR
      REMOVE image
      REMOVE source:name:br
      REMOVE name:br
      REMOVE motorcycle
      REMOVE embankment:right
      REMOVE agricultural
      REMOVE maxspeed:trailer
      REMOVE overtaking:hgv:conditional
      REMOVE embankment
      REMOVE direction
      REMOVE junction:ref
      REMOVE parking:both:orientation
      REMOVE parking:both
      REMOVE zone:maxspeed
      REMOVE noname
      REMOVE junction
      REMOVE wikipedia
      REMOVE wikidata
      REMOVE turn:lanes:forward
      REMOVE lanes:forward
      REMOVE lanes:backward
      REMOVE cycleway:left
      REMOVE cycleway
      REMOVE taxi:lanes
      REMOVE busway
      REMOVE bus:lanes
      REMOVE access:lanes
      REMOVE vehicle
      REMOVE parking:condition:both
      REMOVE name:etymology:wikidata
      REMOVE motor_vehicle
      REMOVE bus
      REMOVE slow_moving
      REMOVE maxspeed:hgv
      REMOVE maxspeed:bus
      REMOVE minspeed
      REMOVE dual_carriageway
      REMOVE tunnel:name
      REMOVE tunnel
      REMOVE destination:int_ref
      REMOVE destination:ref
      REMOVE turn:lanes
      REMOVE cs_dir:forward
      REMOVE avz
      REMOVE voltage
      REMOVE usage
      REMOVE ref:FR:SNCF_Reseau
      REMOVE railway:traffic_mode
      REMOVE railway:track_ref
      REMOVE railway:radio
      REMOVE railway:preferred_direction
      REMOVE railway:kvb
      REMOVE railway:bidirectional
      REMOVE railway
      REMOVE passenger_lines
      REMOVE loading_gauge
      REMOVE importance
      REMOVE gauge
      REMOVE frequency
      REMOVE electrified
      REMOVE survey:date
      REMOVE ref:FR:commune
      REMOVE parking:lane:both
      REMOVE maxweight:lanes
      REMOVE mapillary
      REMOVE lanes:psv
      REMOVE start_date
      REMOVE short_name
      REMOVE destination:ref:lanes
      REMOVE placement
      REMOVE toll:hgv
      REMOVE old_ref
      REMOVE cycleway:both
      REMOVE destination:lanes
      REMOVE stopping
      REMOVE loc_ref
      REMOVE name:nl
      REMOVE nat_ref
      REMOVE loc_name
      REMOVE sac_scale
      REMOVE horse
      REMOVE source:name:oc
      REMOVE source:maxspeed
      REMOVE smoothness
      REMOVE shoulder:right
      REMOVE name:oc
      REMOVE name:fr
      REMOVE operator
      REMOVE shoulder
      REMOVE alt_name
      REMOVE layer
      REMOVE int_ref
      REMOVE bridge
      REMOVE destination:symbol
      REMOVE destination:colour
      REMOVE toll
      REMOVE ref
      REMOVE maxheight
      REMOVE foot
      REMOVE bicycle
      REMOVE maxspeed:type
      REMOVE lane_markings
      REMOVE motorroad
      REMOVE destination
      REMOVE sidewalk
      REMOVE lit
      REMOVE lanes
      REMOVE busway:right
      REMOVE surface
      REMOVE political_division
      REMOVE oneway
      REMOVE maxspeed
      REMOVE highway
      REMOVE cycleway:right
      REMOVE boundary
      REMOVE LARGEUR
      REMOVE TOPONYME
      REMOVE rating
      REMOVE max:abseil
      REMOVE old_name:oc
      REMOVE name:pt
      REMOVE alt_ref
      REMOVE network:type
      REMOVE name:it
      REMOVE pilgrimage
      REMOVE is_in
      REMOVE colour:text
      REMOVE ref:onvvv
      REMOVE symbol:fr
      REMOVE state
      REMOVE proposed:route
      REMOVE ref:FR:aec31
      REMOVE source:colour
      REMOVE sleeping
      REMOVE proposed
      REMOVE air_conditioning
      REMOVE note:network
      REMOVE old_network
      REMOVE descent
      REMOVE ascent
      REMOVE url
      REMOVE name:bg
      REMOVE name:pl
      REMOVE osmc:ref
      REMOVE by_night
      REMOVE roundtrip
      REMOVE distance
      REMOVE via
      REMOVE reservation
      REMOVE network:wikipedia
      REMOVE fee
      REMOVE colour
      REMOVE public_transport:version
      REMOVE symbol
      REMOVE name:sk
      REMOVE name:cs
      REMOVE e-road:class
      REMOVE description:fr
      REMOVE to
      REMOVE from
      REMOVE fid
      REMOVE TOPONYME
      REMOVE Waterway
      REMOVE whitewater:section_name
      REMOVE structure_gauge
      REMOVE seamark:gate:category
      REMOVE diameter
      REMOVE culvert
      REMOVE ref:name
      REMOVE name:right
      REMOVE name:left
      REMOVE name:alt
      REMOVE irrigation
      REMOVE maxheight:marine
      REMOVE seasonal
      REMOVE flow_direction
      REMOVE source:2:url
      REMOVE source:2
      REMOVE source:ref:sandre
      REMOVE note:maxspeed
      REMOVE seamark:type
      REMOVE lock:height
      REMOVE self_service
      REMOVE automated
      REMOVE disused:admin_level
      REMOVE substance
      REMOVE whitewater:section_grade
      REMOVE passage_time
      REMOVE lock_ref
      REMOVE lock_name
      REMOVE lock
      REMOVE nudism
      REMOVE name:hu
      REMOVE disused
      REMOVE source_ref
      REMOVE ref:sandre
      REMOVE tidal
      REMOVE intermittent
      REMOVE CEMT
    USER_EXPOSED_ATTRIBUTES = TOPONYME,Waterway
    -> Reprojector_8
Reprojector_8
    DEST = EPSG:2154
    INTERPOLATION_TYPE_NAME = Nearest Neighbor
    RASTER_CELL_SIZE = Preserve Cells
    RASTER_TOLERANCE = 0.0
    REPROJECTED -> TestFilter_15
TestFilter_15
    DEFAULT_VALUE = <UNFILTERED>
    TEST_LIST = "BOOL_OP,OR,COMPOSITE_TEST,""""""1"""""",TEST_CLAUSE,TEST @Value(OSM_route) = power",power_line,"BOOL_OP,OR,COMPOSITE_TEST,""""""1"""""",TEST_CLAUSE,TEST @Value(OSM_way) = way",way_duplicate
    <UNFILTERED> -> Junction_6
Junction_6
    -> Clipper_3 [CLIPPEE]
Clipper_3
    ATTR_ACCUM_MODE = Merge Clipper
    ATTR_CONFLICT_RES = Use Clippee
    BOUNDARY_CASES = Treat as Inside
    CLEANING_TOLERANCE = Automatic
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeManager_6
AttributeManager_6
    ATTR_TABLE:
      REMOVE left
      REMOVE top
      REMOVE right
      REMOVE bottom
      REMOVE id_parc
      REMOVE surf_ha
      REMOVE surf_m2
      REMOVE proba
      REMOVE com_insee
      REMOVE code_pra
      REMOVE rpg19_gpe
      REMOVE rpg19_cult
      REMOVE rpg18_gpe
      REMOVE rpg18_cult
      REMOVE rpg17_gpe
      REMOVE rpg17_cult
      REMOVE rpg16_gpe
      REMOVE rpg16_cult
      REMOVE rpg15_gpe
      REMOVE rpg15_cult
      REMOVE ID_PARCEL
      REMOVE SURF_PARC
      REMOVE CULTURE_D1
      REMOVE CULTURE_D2
    -> Aggregator
Aggregator
    ACCUM_ATTRS_NAME = Use Attributes From One Feature
    AGGREGATE_TYPE = Homogeneous Collection (If Possible)
    GROUP_BY = CODE_GROUP gc_rpg CLASS_ADM OSM_route OSM_way Railway OSM_Waterway
    MODE = Geometry - Assemble One Level
    SEP = ,
    AGGREGATE -> TestFilter
Aggregator_6
    ACCUM_ATTRS_NAME = Merge Incoming Attributes
    AGGREGATE_TYPE = Homogeneous Collection (If Possible)
    GROUP_BY = _labelDW
    MODE = Geometry - Assemble One Level
    SEP = ,
    AGGREGATE -> TestFilter_4
TestFilter_4
    DEFAULT_VALUE = <UNFILTERED>
    TEST_LIST = "BOOL_OP,OR,COMPOSITE_TEST,""""""1"""""",TEST_CLAUSE,TEST @Value(_labelDW) = 0",Water,"BOOL_OP,OR,COMPOSITE_TEST,""""""1"""""",TEST_CLAUSE,TEST @Value(_labelDW) = 1",Trees,"BOOL_OP,OR,COMPOSITE_TEST,""""""1"""""",TEST_CLAUSE,TEST @Value(_labelDW) = 2",Grass,"BOOL_OP,OR,COMPOSITE_TEST,""""""1"""""",TEST_CLAUSE,TEST @Value(_labelDW) = 3",Flooded_vegetation,"BOOL_OP,OR,COMPOSITE_TEST,""""""1"""""",TEST_CLAUSE,TEST @Value(_labelDW) = 4",Crops,"BOOL_OP,OR,COMPOSITE_TEST,""""""1"""""",TEST_CLAUSE,TEST @Value(_labelDW) = 5",Shrub_and_scrub,"BOOL_OP,OR,COMPOSITE_TEST,""""""1"""""",TEST_CLAUSE,TEST @Value(_labelDW) = 6",Built,"BOOL_OP,OR,COMPOSITE_TEST,""""""1"""""",TEST_CLAUSE,TEST @Value(_labelDW) = 7",Bare,"BOOL_OP,OR,COMPOSITE_TEST,""""""1"""""",TEST_CLAUSE,TEST @Value(_labelDW) = 8",Snow_and_ice
    Trees -> Generalizer_2
    Grass -> Generalizer_2
    Flooded_vegetation -> Generalizer_2
    Crops -> Generalizer_2
    Shrub_and_scrub -> Generalizer_2
    Built -> Generalizer_2
    Bare -> Generalizer_2
    Snow_and_ice -> Generalizer_2
Generalizer_2
    ALG_TEXT = NURBfit (Smooth)
    CLEANING_TOLERANCE = Automatic
    DEGREE = 6
    PRESERVE = Yes
    PRESERVE_PATHS = No
    SEGMENT_LENGTH = 0
    -> Generalizer_4
Generalizer_4
    ALG_TEXT = Douglas (Generalize)
    PRESERVE = No
    PRESERVE_PATHS = No
    TOLERANCE = 3
    -> Aggregator_7
Aggregator_7
    ACCUM_ATTRS_NAME = Merge Incoming Attributes
    AGGREGATE_TYPE = Homogeneous Collection (If Possible)
    GROUP_BY = _labelDW
    MODE = Geometry - Assemble One Level
    SEP = ,
    AGGREGATE -> AttributeManager_4
AttributeManager_4
    -> AreaOnAreaOverlayer [AREA]
Aggregator_2
    ACCUM_ATTRS_NAME = Merge Incoming Attributes
    AGGREGATE_TYPE = Homogeneous Collection (If Possible)
    GROUP_BY = _label
    MODE = Geometry - Assemble One Level
    SEP = ,
    AGGREGATE -> TestFilter_3
TestFilter_3
    DEFAULT_VALUE = <UNFILTERED>
    TEST_LIST = "BOOL_OP,OR,COMPOSITE_TEST,""""""1"""""",TEST_CLAUSE,TEST @Value(_label) = 10",Forest,"BOOL_OP,OR,COMPOSITE_TEST,""""""1"""""",TEST_CLAUSE,TEST @Value(_label) = 20",Shrublnad,"BOOL_OP,OR,COMPOSITE_TEST,""""""1"""""",TEST_CLAUSE,TEST @Value(_label) = 30",Cropland,"BOOL_OP,OR,COMPOSITE_TEST,""""""1"""""",TEST_CLAUSE,TEST @Value(_label) = 40",Grassland,"BOOL_OP,OR,COMPOSITE_TEST,""""""1"""""",TEST_CLAUSE,TEST @Value(_label) = 50",Manmade,"BOOL_OP,OR,COMPOSITE_TEST,""""""1"""""",TEST_CLAUSE,TEST @Value(_label) = 60",Bare,"BOOL_OP,OR,COMPOSITE_TEST,""""""1"""""",TEST_CLAUSE,TEST @Value(_label) = 70",Snow,"BOOL_OP,OR,COMPOSITE_TEST,""""""1"""""",TEST_CLAUSE,TEST @Value(_label) = 80",Water,"BOOL_OP,OR,COMPOSITE_TEST,""""""1"""""",TEST_CLAUSE,TEST @Value(_label) = 90",Herbaceous_wetland,"BOOL_OP,OR,COMPOSITE_TEST,""""""1"""""",TEST_CLAUSE,TEST @Value(_label) = 95",Mangroves,"BOOL_OP,OR,COMPOSITE_TEST,""""""1"""""",TEST_CLAUSE,TEST @Value(_label) = 100",Moss
    Forest -> Generalizer
    Shrublnad -> Generalizer
    Cropland -> Generalizer
    Grassland -> Generalizer
    Manmade -> Generalizer
    Bare -> Generalizer
    Snow -> Generalizer
    Water -> Generalizer
    Herbaceous_wetland -> Generalizer
    Mangroves -> Generalizer
    Moss -> Generalizer
Generalizer
    ALG_TEXT = NURBfit (Smooth)
    DEGREE = 6
    PRESERVE = No
    PRESERVE_PATHS = No
    SEGMENT_LENGTH = 0
    -> Generalizer_3
Generalizer_3
    ALG_TEXT = Douglas (Generalize)
    PRESERVE = No
    PRESERVE_PATHS = No
    TOLERANCE = 3
    -> Aggregator_4
Aggregator_4
    ACCUM_ATTRS_NAME = Merge Incoming Attributes
    AGGREGATE_TYPE = Homogeneous Collection (If Possible)
    GROUP_BY = _label
    MODE = Geometry - Assemble One Level
    SEP = ,
    AGGREGATE -> AttributeManager_5
AttributeManager_5
    ATTR_TABLE:
      REMOVE product_grid
      REMOVE copyright
      REMOVE creation_time
      REMOVE algorithm_version
      REMOVE license
      REMOVE product_tile
      REMOVE title
      REMOVE product_type
      REMOVE reference
      REMOVE time_start
      REMOVE legend
      REMOVE time_end
      REMOVE product_version
      REMOVE product_crs
      REMOVE fme_basename
    -> AreaOnAreaOverlayer [AREA]
AreaOnAreaOverlayer
    ACCUM_ATTRS_NAME = Merge Incoming Attributes
    CLEANING_TOLERANCE = Automatic
    CONNECT_Z_MODE = First Wins
    DEAGGREGATE_INPUT = Yes
    OVC_ATTR = _overlaps
    AREA -> AttributeCreator_5
AttributeCreator_5
    ATTR_TABLE:
      SET_TO Crop2 = FME_CONDITIONAL:DEFAULT_VALUE'_FME_NO_OP_'BOOL_OP;OR;COMPOSITE_TEST;1 OR 2;TEST @Value(_label) = 40;TEST @Value(_labelDW) = 4'Crop'FME_NUM_CONDITIONS2___
      SET_TO Forest2 = FME_CONDITIONAL:DEFAULT_VALUE'_FME_NO_OP_'BOOL_OP;OR;COMPOSITE_TEST;1 OR 2;TEST @Value(_label) = 10;TEST @Value(_labelDW) = 1'Forest'FME_NUM_CONDITIONS2___
      SET_TO Grass2 = FME_CONDITIONAL:DEFAULT_VALUE'_FME_NO_OP_'BOOL_OP;OR;COMPOSITE_TEST;1 OR 2;TEST @Value(_label) = 30;TEST @Value(_labelDW) = 2'Grass'FME_NUM_CONDITIONS2___
      SET_TO Wetland2 = FME_CONDITIONAL:DEFAULT_VALUE'_FME_NO_OP_'BOOL_OP;OR;COMPOSITE_TEST;1 OR 2;TEST @Value(_label) = 90;TEST @Value(_labelDW) = 3'Wetland'FME_NUM_CONDITIONS2___
      SET_TO Soil_low veg2 = FME_CONDITIONAL:DEFAULT_VALUE'_FME_NO_OP_'BOOL_OP;OR;COMPOSITE_TEST;1 OR 2 OR 3 OR 4;TEST @Value(_label) = 20;TEST @Value(_labelDW) = 5;TEST @Value(_label) = 60;TEST @Value(_labelDW) = 7'Soil_low veg'FME_NUM_CONDITIONS2___
      SET_TO Water2 = FME_CONDITIONAL:DEFAULT_VALUE'_FME_NO_OP_'BOOL_OP;OR;COMPOSITE_TEST;1;TEST @Value(_label) = 80'Water'FME_NUM_CONDITIONS2___
      SET_TO Other2 = FME_CONDITIONAL:DEFAULT_VALUE'_FME_NO_OP_'BOOL_OP;OR;COMPOSITE_TEST;1 OR 2 OR 3 OR 4 OR 5 OR 6;TEST @Value(_label) = 50;TEST @Value(_labelDW) = 6;TEST @Value(_label) = 70;TEST @Value(_labelDW) = 8;TEST @Value(_label) = 95;TEST @Value(_label) = 100'Other'FME_NUM_CONDITIONS2___
    -> AttributeManager_10
AttributeManager_10
    NUM_PRIOR_FEATURES = 0
    NUM_SUBSEQUENT_FEATURES = 0
    -> Dissolver_4
Dissolver_4
    ACCUM_INPUT_ATTRS = Merge Incoming Attributes
    CLEANING_TOLERANCE = Automatic
    CONNECT_Z_MODE = First Wins
    DEAGGREGATE_INPUT = Yes
    GROUP_BY = Crop2 Forest2 Grass2 Other2 "Soil_low veg2" Water2 Wetland2
    AREA -> TestFilter
AttributeCreator_6 [off]
    ATTR_TABLE:
      SET_TO Crop_rgp = FME_CONDITIONAL:DEFAULT_VALUE'Others'BOOL_OP;COMPOSITE;COMPOSITE_TEST;1 OR 2 OR 3 OR 4 OR 5 OR 6 OR 7 OR 8 OR 9 OR 10 OR 11 OR 12 OR 13 OR 14;TEST @Value(CODE_CULTU) = BTH;TEST @Value(CODE_CULTU) = BTP;TEST @Value(CODE_CULTU) = BDH;TEST @Value(CODE_CULTU) = BDP;TEST @Value(CODE_CULTU) = BDT;TEST @Value(CODE_CULTU) = MID;TEST @Value(CODE_CULTU) = MIE;TEST @Value(CODE_CULTU) = MIS;TEST @Value(CODE_CULTU) = ORH;TEST @Value(CODE_CULTU) = ORP;TEST @Value(CODE_CULTU) = CZH;TEST @Value(CODE_CULTU) = CZP;TEST @Value(CODE_CULTU) = SOJ;TEST @Value(CODE_GROUP) = 16''FME_NUM_CONDITIONS2___
      SET_TO Forest_rpg = FME_CONDITIONAL:DEFAULT_VALUE'_FME_NO_OP_'BOOL_OP;OR;COMPOSITE_TEST;1;TEST @Value(CODE_GROUP) = 20''FME_NUM_CONDITIONS2___
      SET_TO Grass_rpg = FME_CONDITIONAL:DEFAULT_VALUE'_FME_NO_OP_'BOOL_OP;OR;COMPOSITE_TEST;1 OR 2 OR 3 OR 4 OR 5 OR 6 OR 7;TEST @Value(CODE_GROUP) = 18;TEST @Value(CODE_GROUP) = 19;TEST @Value(CODE_GROUP) = 17;TEST @Value(CODE_CULTU) = BFP;TEST @Value(CODE_CULTU) = BFS;TEST @Value(CODE_CULTU) = BOR;TEST @Value(CODE_CULTU) = BTA''FME_NUM_CONDITIONS2___
      SET_TO Soil_low veg = FME_CONDITIONAL:DEFAULT_VALUE'_FME_NO_OP_'BOOL_OP;OR;COMPOSITE_TEST;1 OR 2 OR 3 OR 4;TEST @Value(CODE_CULTU) = J5M;TEST @Value(CODE_CULTU) = J6P;TEST @Value(CODE_CULTU) = J6S;TEST @Value(CODE_CULTU) = JNO''FME_NUM_CONDITIONS2___
    -> TestFilter [off]
TestFilter
    DEFAULT_VALUE = <UNFILTERED>
    TEST_LIST = "BOOL_OP,COMPOSITE,COMPOSITE_TEST,""""""1"""""",TEST_CLAUSE,TEST CODE_GROUP ATTRIBUTE_HAS_A_VALUE """,CODE_Culture,"BOOL_OP,OR,COMPOSITE_TEST,""""""1"""""",TEST_CLAUSE,TEST gc_rpg ATTRIBUTE_HAS_A_VALUE """,Culture,"BOOL_OP,OR,COMPOSITE_TEST,""""""1"""""",TEST_CLAUSE,TEST CLASS_ADM ATTRIBUTE_HAS_A_VALUE """,Roads_500_IGN,"BOOL_OP,OR,COMPOSITE_TEST,""""""1"""""",TEST_CLAUSE,TEST OSM_route ATTRIBUTE_HAS_A_VALUE """,OSM_route,"BOOL_OP,OR,COMPOSITE_TEST,""""""1"""""",TEST_CLAUSE,TEST OSM_way ATTRIBUTE_HAS_A_VALUE """,OSM_way,"BOOL_OP,OR,COMPOSITE_TEST,""""""1"""""",TEST_CLAUSE,TEST Railway ATTRIBUTE_HAS_A_VALUE """,Railways,"BOOL_OP,OR,COMPOSITE_TEST,""""""1"""""",TEST_CLAUSE,TEST OSM_Waterway ATTRIBUTE_HAS_A_VALUE """,OSM_Waterway,"BOOL_OP,OR,COMPOSITE_TEST,""""""1"""""",TEST_CLAUSE,TEST Crop2 ATTRIBUTE_HAS_A_VALUE """,Crop2,"BOOL_OP,OR,COMPOSITE_TEST,""""""1"""""",TEST_CLAUSE,TEST Grass2 ATTRIBUTE_HAS_A_VALUE """,Grass2,"BOOL_OP,OR,COMPOSITE_TEST,""""""1"""""",TEST_CLAUSE,TEST Forest2 ATTRIBUTE_HAS_A_VALUE """,Forest2,"BOOL_OP,OR,COMPOSITE_TEST,""""""1"""""",TEST_CLAUSE,TEST Water2 ATTRIBUTE_HAS_A_VALUE """,Water2,"BOOL_OP,OR,COMPOSITE_TEST,""""""1"""""",TEST_CLAUSE,TEST Wetland2 ATTRIBUTE_HAS_A_VALUE """,Wetland2,"BOOL_OP,OR,COMPOSITE_TEST,""""""1"""""",TEST_CLAUSE,TEST Soil_low veg2 ATTRIBUTE_HAS_A_VALUE """,Soil_low veg2,"BOOL_OP,OR,COMPOSITE_TEST,""""""1"""""",TEST_CLAUSE,TEST Other2 ATTRIBUTE_HAS_A_VALUE """,Other2
    CODE_Culture -> Aggregator_8
    CODE_Culture -> Clipper [CLIPPEE]
    Culture -> Aggregator_8
    Culture -> Clipper [CLIPPEE]
    Roads_500_IGN -> Aggregator_8
    Roads_500_IGN -> Aggregator_5
    OSM_route -> Aggregator_8
    OSM_route -> Aggregator_5
    OSM_way -> Aggregator_8
    OSM_way -> Aggregator_5
    Railways -> Aggregator_5
    Railways -> Aggregator_8
    OSM_Waterway -> Aggregator_8
    OSM_Waterway -> Aggregator_5
    Crop2 -> Clipper_2 [CLIPPEE]
    Grass2 -> Clipper_2 [CLIPPEE]
    Forest2 -> Clipper_2 [CLIPPEE]
    Water2 -> Clipper_2 [CLIPPEE]
    Wetland2 -> Clipper_2 [CLIPPEE]
    Soil_low veg2 -> Clipper_2 [CLIPPEE]
    Other2 -> Clipper_2 [CLIPPEE]
Aggregator_5
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    OUTSIDE -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator_4
AreaCalculator_4
    AREA_ATTR = _area_RPGs
    AREA_TYPE = Plane Area
    MULT = 1
    -> Tester_2
Tester_2
    BOOL_OP = OR
    COMPOSITE_TEST = 1
    TEST_CLAUSE = TEST @Value(_area_RPGs) >= 1
    TEST_MODE = TEST
    PASSED -> AttributeManager_8
AttributeManager_8
    ATTR_TABLE:
      REMOVE _label
      REMOVE _area
      REMOVE _fme_no_clipper
      REMOVE CLASS_ADM
      REMOVE OSM_route
      REMOVE OSM_way
      REMOVE Railway
      REMOVE _clipped
      REMOVE _geometry_name
      REMOVE _part_number
    -> AreaGapAndOverlapCleaner
Aggregator_8
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> Clipper_2 [CLIPPER]
Clipper_2
    ATTR_ACCUM_MODE = Merge Clipper
    ATTR_CONFLICT_RES = Use Clippee
    BOUNDARY_CASES = Treat as Inside and Outside
    CLEANING_TOLERANCE = Automatic
    CLIP_TYPE = Multiple Clippers
    LINES_AS_SEGMENTS = No
    MEASURE_TYPE = Continuous
    MISSING_VAL_MODE = Compute
    PRESERVE_CLIPPEE_EXTENTS = No
    VAL_SOURCE = Clippee Only
    OUTSIDE -> SpikeRemover_2
SpikeRemover_2
    DIMENSIONS = 2D
    ITERATIVE = Yes
    SPIKEANGLE = 10
    SPIKELENGTH = 250
    UNCHANGED -> AttributeManager_7
    CHANGED -> AttributeManager_7
AttributeManager_7
    ATTR_TABLE:
      REMOVE _area
      REMOVE _fme_no_clipper
      REMOVE CLASS_ADM
      REMOVE OSM_route
      REMOVE OSM_way
      REMOVE Railway
      REMOVE CODE_GROUP
      REMOVE gc_rpg
      REMOVE id
      REMOVE fid
      REMOVE CODE_CULTU
      REMOVE culture
      REMOVE OSM_Waterway
    -> Deaggregator_2
Deaggregator_2
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator_6
AreaCalculator_6
    AREA_ATTR = _area_LCLU
    AREA_TYPE = Plane Area
    MULT = 1
    -> TestFilter_7
TestFilter_7
    DEFAULT_VALUE = <UNFILTERED>
    TEST_LIST = "BOOL_OP,OR,COMPOSITE_TEST,""""""1"""""",TEST_CLAUSE,TEST Crop2 ATTRIBUTE_HAS_A_VALUE """,Crop2,"BOOL_OP,OR,COMPOSITE_TEST,""""""1"""""",TEST_CLAUSE,TEST Grass2 ATTRIBUTE_HAS_A_VALUE """,Grass2,"BOOL_OP,OR,COMPOSITE_TEST,""""""1"""""",TEST_CLAUSE,TEST Forest2 ATTRIBUTE_HAS_A_VALUE """,Forest2,"BOOL_OP,OR,COMPOSITE_TEST,""""""1"""""",TEST_CLAUSE,TEST Water2 ATTRIBUTE_HAS_A_VALUE """,Water2,"BOOL_OP,OR,COMPOSITE_TEST,""""""1"""""",TEST_CLAUSE,TEST Wetland2 ATTRIBUTE_HAS_A_VALUE """,Wetland2,"BOOL_OP,OR,COMPOSITE_TEST,""""""1"""""",TEST_CLAUSE,TEST Soil_low veg2 ATTRIBUTE_HAS_A_VALUE """,Soil_low veg2,"BOOL_OP,OR,COMPOSITE_TEST,""""""1"""""",TEST_CLAUSE,TEST Other2 ATTRIBUTE_HAS_A_VALUE """,Other2
    Crop2 -> Tester_6
    Grass2 -> Tester_6
    Forest2 -> Aggregator_3
    Water2 -> Aggregator_3
    Wetland2 -> Aggregator_3
    Soil_low veg2 -> Aggregator_3
    Other2 -> Aggregator_3
Tester_6
    BOOL_OP = OR
    COMPOSITE_TEST = 1
    TEST_CLAUSE = TEST @Value(_area_LCLU) >= 1000
    TEST_MODE = TEST
    PASSED -> Aggregator_3
Aggregator_3
    ACCUM_ATTRS_NAME = Merge Incoming Attributes
    AGGREGATE_TYPE = Homogeneous Collection (If Possible)
    GROUP_BY = Crop2 Forest2 Grass2 Other2 "Soil_low veg2" Water2 Wetland2
    MODE = Geometry - Assemble One Level
    SEP = ,
    AGGREGATE -> Bufferer_11
Bufferer_11
    ANGLE = 22.5
    CAP_STYLE = None
    CORNER_STYLE = Miter
    MITER_LIMIT = 3
    MODE = AREA
    OFFSET = -1
    OFFSET_UNITS = NONE
    PRECISION = APPROX
    BUFFERED -> Aggregator_9
Aggregator_9
    ACCUM_ATTRS_NAME = Use Attributes From One Feature
    AGGREGATE_TYPE = Homogeneous Collection (If Possible)
    GROUP_BY = Crop2 Forest2 Grass2 Other2 "Soil_low veg2" Water2 Wetland2
    MODE = Geometry - Assemble One Level
    SEP = ,
    AGGREGATE -> Bufferer_13
Bufferer_13
    ANGLE = 22.5
    CAP_STYLE = None
    CORNER_STYLE = Miter
    MITER_LIMIT = 3
    MODE = AREA
    OFFSET = 1
    OFFSET_UNITS = NONE
    PRECISION = APPROX
    BUFFERED -> Deaggregator_3
Deaggregator_3
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator_8
AreaCalculator_8
    AREA_ATTR = _area_cleaning
    AREA_TYPE = Plane Area
    MULT = 1
    -> Tester_8
Tester_8
    BOOL_OP = OR
    COMPOSITE_TEST = 1
    TEST_CLAUSE = TEST @Value(_area_cleaning) >= 100
    TEST_MODE = TEST
    PASSED -> CircularityCalculator
CircularityCalculator
    CALC_GEOM_DISP = Feature Boundary
    CIRC_ATTR = _circularity
    -> AreaCalculator_10
AreaCalculator_10
    AREA_ATTR = _area_circular
    AREA_TYPE = Plane Area
    MULT = 1
    -> AttributeRounder_4
AttributeRounder_4
    PLACES = 1
    ROUND_TYPE = Nearest
    SRC_ATTRS = _circularity _area_circular
    -> Tester_12
Tester_12
    BOOL_OP = COMPOSITE
    COMPOSITE_TEST = 1 AND 2
    TEST_CLAUSE:
      TEST @Value(_circularity) < 0.1
      TEST @Value(_area_cleaning) <= 10000
    TEST_MODE = TEST
    FAILED -> Junction_4
Junction_4
    -> Bufferer_16
    -> AreaOnAreaOverlayer_3 [AREA]
Bufferer_16
    ANGLE = 22.5
    CAP_STYLE = None
    CORNER_STYLE = Miter
    MITER_LIMIT = 3
    MODE = AREA
    OFFSET = -2
    OFFSET_UNITS = NONE
    PRECISION = APPROX
    BUFFERED -> Deaggregator_5
Deaggregator_5
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> CircularityCalculator_2
CircularityCalculator_2
    CALC_GEOM_DISP = Feature Boundary
    CIRC_ATTR = _circularityyyyyy
    -> AreaCalculator_11
AreaCalculator_11
    AREA_ATTR = _areaaaaaaaaaaa
    AREA_TYPE = Plane Area
    MULT = 1
    -> AttributeRounder_5
AttributeRounder_5
    PLACES = 1
    ROUND_TYPE = Nearest
    SRC_ATTRS = _areaaaaaaaaaaa _circularityyyyyy
    -> Tester_13
Tester_13
    BOOL_OP = COMPOSITE
    COMPOSITE_TEST = 1 AND 2
    TEST_CLAUSE:
      TEST @Value(_circularityyyyyy) < 0.2
      TEST @Value(_areaaaaaaaaaaa) <= 10000
    TEST_MODE = TEST
    PASSED -> Bufferer_17
Bufferer_17
    ANGLE = 22.5
    CAP_STYLE = None
    CORNER_STYLE = Miter
    MITER_LIMIT = 3
    MODE = AREA
    OFFSET = 2
    OFFSET_UNITS = NONE
    PRECISION = APPROX
    BUFFERED -> AreaOnAreaOverlayer_3 [AREA]
AreaOnAreaOverlayer_3
    ACCUM_ATTRS_NAME = Merge Incoming Attributes
    CLEANING_TOLERANCE = Automatic
    CONNECT_Z_MODE = First Wins
    DEAGGREGATE_INPUT = Yes
    OVC_ATTR = _overlaps
    AREA -> CircularityCalculator_3
CircularityCalculator_3
    CALC_GEOM_DISP = Feature Boundary
    CIRC_ATTR = _circularity_Final
    -> AttributeRounder_6
AttributeRounder_6
    PLACES = 1
    ROUND_TYPE = Nearest
    SRC_ATTRS = _circularity_Final
    -> AreaGapAndOverlapCleaner
AreaGapAndOverlapCleaner
    CLEANING_TOLERANCE = Automatic
    CONNECT_Z_MODE = First Wins
    DEAGGREGATE_INPUT = YES
    FILL_ALL_GAPS = No
    MEASURE_TYPE = Continuous
    MISSING_VAL_MODE = Compute
    REPAIR_METHOD = Longest Boundary
    REPAIRED -> AttributeCreator_7
AttributeCreator_7
    ATTR_TABLE:
      SET_TO Crop_rgp = FME_CONDITIONAL:DEFAULT_VALUE'_FME_NO_OP_'BOOL_OP;OR;COMPOSITE_TEST;1 OR 2 OR 3 OR 4 OR 5 OR 6 OR 7 OR 8 OR 9 OR 10 OR 11 OR 12 OR 13 OR 14 OR 15 OR 16 OR 17 OR 18 OR 19;TEST @Value(CODE_CULTU) = BTH;TEST @Value(CODE_CULTU) = BTP;TEST @Value(CODE_CULTU) = BDH;TEST @Value(CODE_CULTU) = BDP;TEST @Value(CODE_CULTU) = BDT;TEST @Value(CODE_CULTU) = MID;TEST @Value(CODE_CULTU) = MIE;TEST @Value(CODE_CULTU) = MIS;TEST @Value(CODE_CULTU) = ORH;TEST @Value(CODE_CULTU) = ORP;TEST @Value(CODE_CULTU) = CZH;TEST @Value(CODE_CULTU) = CZP;TEST @Value(CODE_CULTU) = SOJ;TEST @Value(CODE_GROUP) = 16;TEST @Value(culture) = Ble;TEST @Value(culture) = Colza;TEST @Value(culture) = Mais;TEST @Value(culture) = Soja;TEST @Value(culture) = Fourrages'Crop_rpg'BOOL_OP;OR;COMPOSITE_TEST;1 OR 2 OR 3 OR 4 OR 5 OR 6 OR 7 OR 8 OR 9 OR 10 OR 11 OR 12 OR 13 OR 14 OR 15 OR 16 OR 17 OR 18 OR 19 OR 20 OR 21 OR 22 OR 23 OR 24 OR 25 OR 26 OR 27 OR 28 OR 29 OR 30;TEST @Value(culture) = Autres cereales;TEST @Value(culture) = Divers (Volailles);TEST @Value(culture) = Fleurs;TEST @Value(culture) = Fruits a coque;TEST @Value(culture) = Haras;TEST @Value(culture) = Jardin collectif;TEST @Value(culture) = Jardin individuel;TEST @Value(culture) = Landes;TEST @Value(culture) = Legumes;TEST @Value(culture) = Legumes (Serre);TEST @Value(culture) = Proteagineux;TEST @Value(culture) = SNE;TEST @Value(culture) = SPH;TEST @Value(culture) = Tournesol;TEST @Value(CODE_CULTU) = TRN;TEST @Value(CODE_CULTU) = TTH;TEST @Value(CODE_CULTU) = FVL;TEST @Value(CODE_GROUP) = 28;TEST @Value(CODE_GROUP) = 26;TEST @Value(CODE_GROUP) = 25;TEST @Value(CODE_GROUP) = 24;TEST @Value(CODE_GROUP) = 23;TEST @Value(CODE_GROUP) = 22;TEST @Value(CODE_GROUP) = 15;TEST @Value(CODE_GROUP) = 14;TEST @Value(CODE_GROUP) = 11;TEST @Value(CODE_GROUP) = 9;TEST @Value(CODE_GROUP) = 8;TEST @Value(CODE_GROUP) = 7;TEST @Value(CODE_GROUP) = 4'Other_Crop_rpg'FME_NUM_CONDITIONS3___
      SET_TO Grass_rpg = FME_CONDITIONAL:DEFAULT_VALUE'_FME_NO_OP_'BOOL_OP;OR;COMPOSITE_TEST;1 OR 2 OR 3 OR 4 OR 5 OR 6 OR 7 OR 8 OR 9 OR 10;TEST @Value(culture) = Prairie;TEST @Value(culture) = Prairie temporaire;TEST @Value(culture) = Prairie (Chevaux);TEST @Value(CODE_CULTU) = BFP;TEST @Value(CODE_CULTU) = BFS;TEST @Value(CODE_CULTU) = BOR;TEST @Value(CODE_CULTU) = BTA;TEST @Value(CODE_GROUP) = 18;TEST @Value(CODE_GROUP) = 19;TEST @Value(CODE_GROUP) = 17'Grass_rpg 'FME_NUM_CONDITIONS2___
      SET_TO Forest_rpg = FME_CONDITIONAL:DEFAULT_VALUE'_FME_NO_OP_'BOOL_OP;OR;COMPOSITE_TEST;1 OR 2 OR 3;TEST @Value(CODE_GROUP) = 20;TEST @Value(culture) = Vergers;TEST @Value(CODE_GROUP) = 21'Forest_rpg 'FME_NUM_CONDITIONS2___
      SET_TO Soil_low veg_rpg = FME_CONDITIONAL:DEFAULT_VALUE'_FME_NO_OP_'BOOL_OP;OR;COMPOSITE_TEST;1 OR 2 OR 3 OR 4 OR 5;TEST @Value(CODE_CULTU) = J5M;TEST @Value(CODE_CULTU) = J6P;TEST @Value(CODE_CULTU) = J6S;TEST @Value(CODE_CULTU) = JNO;TEST @Value(culture) = Jachere'Soil_low veg_rpg'FME_NUM_CONDITIONS2___
      SET_TO Batiment_culture_rpg = FME_CONDITIONAL:DEFAULT_VALUE'_FME_NO_OP_'BOOL_OP;OR;COMPOSITE_TEST;1;TEST @Value(culture) = Batiment elevage'Batiment elevage'FME_NUM_CONDITIONS2___
    -> AttributeManager_9
AttributeManager_9
    NUM_PRIOR_FEATURES = 0
    NUM_SUBSEQUENT_FEATURES = 0
    -> Bufferer_14
Bufferer_14
    ANGLE = 22.5
    CAP_STYLE = None
    CORNER_STYLE = Miter
    MITER_LIMIT = 3
    MODE = AREA
    OFFSET = 0.5
    OFFSET_UNITS = NONE
    PRECISION = APPROX
    BUFFERED -> Bufferer_15
Bufferer_15
    ANGLE = 22.5
    CAP_STYLE = None
    CORNER_STYLE = Miter
    MITER_LIMIT = 3
    MODE = AREA
    OFFSET = -0.5
    OFFSET_UNITS = NONE
    PRECISION = APPROX
    BUFFERED -> TestFilter_9
TestFilter_9
    DEFAULT_VALUE = <UNFILTERED>
    TEST_LIST = "BOOL_OP,OR,COMPOSITE_TEST,""""""1"""""",TEST_CLAUSE,TEST Crop2 ATTRIBUTE_HAS_A_VALUE """,Crop2,"BOOL_OP,OR,COMPOSITE_TEST,""""""1"""""",TEST_CLAUSE,TEST Grass2 ATTRIBUTE_HAS_A_VALUE """,Grass2,"BOOL_OP,OR,COMPOSITE_TEST,""""""1"""""",TEST_CLAUSE,TEST Forest2 ATTRIBUTE_HAS_A_VALUE """,Forest2,"BOOL_OP,OR,COMPOSITE_TEST,""""""1"""""",TEST_CLAUSE,TEST Water2 ATTRIBUTE_HAS_A_VALUE """,Water2,"BOOL_OP,OR,COMPOSITE_TEST,""""""1"""""",TEST_CLAUSE,TEST Wetland2 ATTRIBUTE_HAS_A_VALUE """,Wetland2,"BOOL_OP,OR,COMPOSITE_TEST,""""""1"""""",TEST_CLAUSE,TEST Soil_low veg2 ATTRIBUTE_HAS_A_VALUE """,Soil_low veg2,"BOOL_OP,OR,COMPOSITE_TEST,""""""1"""""",TEST_CLAUSE,TEST Other2 ATTRIBUTE_HAS_A_VALUE """,Other2,"BOOL_OP,OR,COMPOSITE_TEST,""""""1"""""",TEST_CLAUSE,TEST Crop_rgp ATTRIBUTE_HAS_A_VALUE """,Crop_rgp,"BOOL_OP,OR,COMPOSITE_TEST,""""""1"""""",TEST_CLAUSE,TEST Grass_rpg ATTRIBUTE_HAS_A_VALUE """,Grass_rpg,"BOOL_OP,OR,COMPOSITE_TEST,""""""1"""""",TEST_CLAUSE,TEST Soil_low veg_rpg ATTRIBUTE_HAS_A_VALUE """,Soil_low veg_rpg,"BOOL_OP,OR,COMPOSITE_TEST,""""""1"""""",TEST_CLAUSE,TEST Forest_rpg ATTRIBUTE_HAS_A_VALUE """,Forest_rpg,"BOOL_OP,OR,COMPOSITE_TEST,""""""1"""""",TEST_CLAUSE,TEST Batiment_culture_rpg ATTRIBUTE_HAS_A_VALUE """,Batiment_culture_rpg
    Crop2 -> AreaCalculator_5
    Grass2 -> AreaCalculator_5
    Forest2 -> Junction_5
    Water2 -> AreaCalculator_5
    Wetland2 -> AreaCalculator_5
    Soil_low veg2 -> AreaCalculator_5
    Other2 -> AreaCalculator_5
    Crop_rgp -> Junction_5
    Grass_rpg -> Junction_5
    Soil_low veg_rpg -> Junction_5
    Forest_rpg -> Junction_5
    Batiment_culture_rpg -> Junction_5
    <UNFILTERED> -> AreaCalculator_5
AreaCalculator_5
    AREA_ATTR = _area_area
    AREA_TYPE = Plane Area
    MULT = 1
    -> Tester_4
Tester_4
    BOOL_OP = OR
    COMPOSITE_TEST = 1
    TEST_CLAUSE = TEST @Value(_area_area) >= 1000
    TEST_MODE = TEST
    PASSED -> DonutHoleExtractor_2
DonutHoleExtractor_2
    DEAGGREGATE_INPUT = Yes
    OUTERSHELL -> Junction_5
Junction_5
    -> Deaggregator_4
Deaggregator_4
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator_7
AreaCalculator_7
    AREA_ATTR = _area_Hulle_3
    AREA_TYPE = Plane Area
    MULT = 1
    -> TestFilter_6
TestFilter_6
    DEFAULT_VALUE = <UNFILTERED>
    TEST_LIST = "BOOL_OP,OR,COMPOSITE_TEST,""""""1"""""",TEST_CLAUSE,TEST Crop_rgp ATTRIBUTE_HAS_A_VALUE """,Crop_rgp,"BOOL_OP,OR,COMPOSITE_TEST,""""""1"""""",TEST_CLAUSE,TEST Grass_rpg ATTRIBUTE_HAS_A_VALUE """,Grass_rpg,"BOOL_OP,OR,COMPOSITE_TEST,""""""1"""""",TEST_CLAUSE,TEST Forest_rpg ATTRIBUTE_HAS_A_VALUE """,Forest_rpg,"BOOL_OP,OR,COMPOSITE_TEST,""""""1"""""",TEST_CLAUSE,TEST Soil_low veg_rpg ATTRIBUTE_HAS_A_VALUE """,Soil_low veg_rpg,"BOOL_OP,OR,COMPOSITE_TEST,""""""1"""""",TEST_CLAUSE,TEST Batiment_culture_rpg ATTRIBUTE_HAS_A_VALUE """,Batiment_culture_rpg,"BOOL_OP,OR,COMPOSITE_TEST,""""""1"""""",TEST_CLAUSE,TEST Crop2 ATTRIBUTE_HAS_A_VALUE """,Crop2,"BOOL_OP,OR,COMPOSITE_TEST,""""""1"""""",TEST_CLAUSE,TEST Grass2 ATTRIBUTE_HAS_A_VALUE """,Grass2,"BOOL_OP,OR,COMPOSITE_TEST,""""""1"""""",TEST_CLAUSE,TEST Forest2 ATTRIBUTE_HAS_A_VALUE """,Forest2,"BOOL_OP,OR,COMPOSITE_TEST,""""""1"""""",TEST_CLAUSE,TEST Water2 ATTRIBUTE_HAS_A_VALUE """,Water2,"BOOL_OP,OR,COMPOSITE_TEST,""""""1"""""",TEST_CLAUSE,TEST Wetland2 ATTRIBUTE_HAS_A_VALUE """,Wetland2,"BOOL_OP,OR,COMPOSITE_TEST,""""""1"""""",TEST_CLAUSE,TEST Soil_low veg2 ATTRIBUTE_HAS_A_VALUE """,Soil_low veg2,"BOOL_OP,OR,COMPOSITE_TEST,""""""1"""""",TEST_CLAUSE,TEST Other2 ATTRIBUTE_HAS_A_VALUE """,Other2,"BOOL_OP,OR,COMPOSITE_TEST,""""""1"""""",TEST_CLAUSE,TEST @Value(Crop_rgp) = Other_Crop_rpg",Other_Crop_rpg
    Crop_rgp -> Deaggregator_8
    Grass_rpg -> Deaggregator_8
    Forest_rpg -> Deaggregator_8
    Soil_low veg_rpg -> Deaggregator_8
    Batiment_culture_rpg -> Deaggregator_8
    Crop2 -> Tester_9
    Grass2 -> Tester_9
    Forest2 -> Tester_11
    Water2 -> Deaggregator_8
    Wetland2 -> Deaggregator_8
    Soil_low veg2 -> Deaggregator_8
    Other2 -> Deaggregator_8
Tester_11
    BOOL_OP = OR
    COMPOSITE_TEST = 1
    TEST_CLAUSE = TEST @Value(_area_Hulle_3) >= 1
    TEST_MODE = TEST
    PASSED -> Deaggregator_8
Tester_9
    BOOL_OP = OR
    COMPOSITE_TEST = 1
    TEST_CLAUSE = TEST @Value(_area_Hulle_3) >= 1000
    TEST_MODE = TEST
    PASSED -> Deaggregator_8
PythonCaller [off]
    PYTHONSOURCE:
      import fme
      import fmeobjects
      import math

      # Define FME_GEOM_POLYGON as a constant
      FME_GEOM_POLYGON = 3  # Replace with the appropriate value for the polygon feature type

      class FeatureProcessor(object):
          def __init__(self):
              """Base constructor for class members."""
              pass

          def remove_spikes(self, vertices, epsilon):
              """Remove spikes from a polygon using the Ramer-Douglas-Peucker algorithm.
              :param list of tuple vertices: The vertices of the polygon.
              :param float epsilon: The tolerance parameter for removing spikes.
              :return: The new vertices after removing spikes.
              :rtype: list of tuple
              """
              def distance(p1, p2):
                  # Calculate the Euclidean distance between two points (vertices)
                  return math.sqrt((p2[0] - p1[0])**2 + (p2[1] - p1[1])**2)

              def rdp_simplify_polygon(points, epsilon):
                  # Recursive implementation of the Ramer-Douglas-Peucker algorithm
                  # Check if the list of points is empty or has only two points
                  if len(points) <= 2:
                      return points

                  # Find the point with the maximum distance from the line formed by the endpoints
                  d_max = 0
                  index = 0
                  for i in range(1, len(points) - 1):
                      d = distance(points[0], points[-1]) - distance(points[0], points[i])
                      if d > d_max:
                          d_max = d
                          index = i

                  # If the maximum distance is greater than the epsilon, recursively simplify both segments
                  if d_max > epsilon:
                      simplified_points1 = rdp_simplify_polygon(points[:index + 1], epsilon)
                      simplified_points2 = rdp_simplify_polygon(points[index:], epsilon)
                      return simplified_points1[:-1] + simplified_points2

                  # If the maximum distance is not greater than the epsilon, return the endpoints only
                  return [points[0], points[-1]]

              return rdp_simplify_polygon(vertices, epsilon)

          def merge_small_gaps(self, feature):
              """Merge small gaps in the polygon with neighboring polygons.
              :param fmeobjects.FMEFeature feature: The polygon feature.
              :return: The merged feature after filling small gaps.
              :rtype: fmeobjects.FMEFeature
              """
              def merge_polygons(geom1, geom2):
                  # Merge two polygon geometries by adding the vertices of the second geometry to the first one
                  merged_geom = geom1
                  merged_geom.addPolygon(geom2.getVertices())
                  return merged_geom

              neighboring_polygons = self.find_neighboring_polygons(feature)
              if neighboring_polygons:
                  # Initialize a list to store the merged polygons
                  merged_polygons = []

                  # Check if there are small neighboring polygons to merge
                  while neighboring_polygons:
                      small_polygon = None
                      large_polygon = None

                      # Find a small neighboring polygon to merge
                      for neighbor_polygon in neighboring_polygons:
                          area_threshold = 5000  # Example threshold area in square units
                          if neighbor_polygon.getArea() < area_threshold:
                              small_polygon = neighbor_polygon
                              break

                      # If there is a small polygon, find a larger neighboring polygon to merge it with
                      if small_polygon:
                          for neighbor_polygon in neighboring_polygons:
                              if neighbor_polygon != small_polygon:
                                  if large_polygon is None or neighbor_polygon.getArea() > large_polygon.getArea():
                                      large_polygon = neighbor_polygon

                      # If a large polygon is found, merge the small polygon into the larger one
                      if small_polygon and large_polygon:
                          merged_geometry = merge_polygons(large_polygon.getGeometry(), small_polygon.getGeometry())
                          merged_polygon = fmeobjects.FMEFeature()
                          merged_polygon.setGeometry(merged_geometry)
                          # Store the merged polygon for further iterations
                          merged_polygons.append(merged_polygon)

                          # Remove the small polygon from the list of neighboring polygons
                          neighboring_polygons.remove(small_polygon)

                  # Update the feature geometry with the final merged geometry
                  if merged_polygons:
                      merged_geometry = feature.getGeometry()
                      for merged_polygon in merged_polygons:
                          merged_geometry = merge_polygons(merged_geometry, merged_polygon.getGeometry())
                      feature.setGeometry(merged_geometry)

              return feature

          def refine_polygon_geometry(self, geometry):
              # Refine the geometry of the polygon feature
              # You need to implement this method based on the specific refinement and smoothing techniques you want to use.
              # One approach is to use methods like buffer, simplify, or smoothing algorithms to refine the geometry.
              # For example, you can use the simplify method from Shapely library to simplify the polygon geometry.
              # You can adjust the tolerance parameter for the desired level of simplification.
              # Note: Make sure to import the necessary libraries for the operations.
              refined_geometry = geometry  # Placeholder, replace this with the actual refinement process
              # ... (Logic to refine and smooth the geometry) ...
              return refined_geometry

          def refine_and_smooth(self, feature):
              """Refine and smooth the geometry of the polygon feature.
              :param fmeobjects.FMEFeature feature: The polygon feature.
              :return: The refined and smoothed feature.
              :rtype: fmeobjects.FMEFeature
              """
              # Get the geometry of the feature
              geom = feature.getGeometry()
              # Refine and smooth the geometry
              refined_geom = self.refine_polygon_geometry(geom)
              # Update the geometry of the feature with the refined one
              feature.setGeometry(refined_geom)
              return feature

          def input(self, feature):
              # Check if the feature is a polygon
              if feature.getFeatureType() == FME_GEOM_POLYGON:
                  # Get the geometry of the feature
                  geom = feature.getGeometry()
                  # Get the vertices of the polygon
                  vertices = geom.getVertices()
                  # Call the method to remove spikes
                  epsilon = 0.5  # Adjust as needed for removing spikes
                  new_vertices = self.remove_spikes(vertices, epsilon)
                  # Set the new vertices for the feature
                  new_geom = fmeobjects.FMEGeometry()
                  new_geom.addPolygon(new_vertices)
                  feature.setGeometry(new_geom)
                  # Merge small gaps and refine/smooth the polygon
                  feature = self.merge_small_gaps(feature)
                  feature = self.refine_and_smooth(feature)
              # Emit the processed feature
              self.pyoutput(feature)

          def close(self):
              """This method is called once all the FME Features have been processed
              from input().
              """
              pass

          def process_group(self):
              """When 'Group By' attribute(s) are specified, this method is called
              once all the FME Features in a current group have been sent to input().
              FME Features sent to input() should generally be cached for group-by
              processing in this method when knowledge of all Features is required.
              The resulting Feature(s) from the group-by processing should be emitted
              through self.pyoutput().
              FME will continue calling input() a number of times followed
              by process_group() for each 'Group By' attribute, so this
              implementation should reset any class members for the next group.
              """
              pass
    PYTHONSYMBOL = FeatureProcessor
DonutBuilder_2 [off]
    CONNECT_Z_MODE = First Wins
    DROP = no
    FLAG_ATTR = _hole_flag
    AREA -> Deaggregator_8 [off]
Deaggregator_8
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator_9
AreaCalculator_9
    AREA_ATTR = _area_Hulle_3
    AREA_TYPE = Plane Area
    MULT = 1
    -> AttributeManager_11
AttributeManager_11
    ATTR_TABLE:
      REMOVE _hole_flag
      REMOVE id
      REMOVE fid
      REMOVE OSM_Waterway
      REMOVE fme_basename
      REMOVE _overlaps
      REMOVE _geometry_name
      REMOVE _part_number
    -> TestFilter_10
TestFilter_10
    DEFAULT_VALUE = <UNFILTERED>
    TEST_LIST = "BOOL_OP,OR,COMPOSITE_TEST,""""""1"""""",TEST_CLAUSE,TEST Crop_rgp ATTRIBUTE_HAS_A_VALUE """,Crop_rgp,"BOOL_OP,OR,COMPOSITE_TEST,""""""1"""""",TEST_CLAUSE,TEST Grass_rpg ATTRIBUTE_HAS_A_VALUE """,Grass_rpg,"BOOL_OP,OR,COMPOSITE_TEST,""""""1"""""",TEST_CLAUSE,TEST Forest_rpg ATTRIBUTE_HAS_A_VALUE """,Forest_rpg,"BOOL_OP,OR,COMPOSITE_TEST,""""""1"""""",TEST_CLAUSE,TEST Soil_low veg_rpg ATTRIBUTE_HAS_A_VALUE """,Soil_low veg_rpg,"BOOL_OP,OR,COMPOSITE_TEST,""""""1"""""",TEST_CLAUSE,TEST Batiment_culture_rpg ATTRIBUTE_HAS_A_VALUE """,Batiment_culture_rpg,"BOOL_OP,OR,COMPOSITE_TEST,""""""1"""""",TEST_CLAUSE,TEST Crop2 ATTRIBUTE_HAS_A_VALUE """,Crop2,"BOOL_OP,OR,COMPOSITE_TEST,""""""1"""""",TEST_CLAUSE,TEST Grass2 ATTRIBUTE_HAS_A_VALUE """,Grass2,"BOOL_OP,OR,COMPOSITE_TEST,""""""1"""""",TEST_CLAUSE,TEST Forest2 ATTRIBUTE_HAS_A_VALUE """,Forest2,"BOOL_OP,OR,COMPOSITE_TEST,""""""1"""""",TEST_CLAUSE,TEST Water2 ATTRIBUTE_HAS_A_VALUE """,Water2,"BOOL_OP,OR,COMPOSITE_TEST,""""""1"""""",TEST_CLAUSE,TEST Wetland2 ATTRIBUTE_HAS_A_VALUE """,Wetland2,"BOOL_OP,OR,COMPOSITE_TEST,""""""1"""""",TEST_CLAUSE,TEST Soil_low veg2 ATTRIBUTE_HAS_A_VALUE """,Soil_low veg2,"BOOL_OP,OR,COMPOSITE_TEST,""""""1"""""",TEST_CLAUSE,TEST Other2 ATTRIBUTE_HAS_A_VALUE """,Other2
    Crop_rgp -> AreaOnAreaOverlayer_2 [AREA]
    Grass_rpg -> AreaOnAreaOverlayer_2 [AREA]
    Forest_rpg -> AreaOnAreaOverlayer_2 [AREA]
    Soil_low veg_rpg -> AreaOnAreaOverlayer_2 [AREA]
    Batiment_culture_rpg -> AreaOnAreaOverlayer_2 [AREA]
    Crop2 -> Tester_10
    Grass2 -> Tester_10
    Forest2 -> AreaOnAreaOverlayer_2 [AREA]
    Water2 -> Tester_10
    Wetland2 -> Tester_10
    Soil_low veg2 -> Tester_10
    Other2 -> Tester_10
Tester_10
    BOOL_OP = OR
    COMPOSITE_TEST = 1
    TEST_CLAUSE = TEST @Value(_area_Hulle_3) >= 1000
    TEST_MODE = TEST
    PASSED -> AreaOnAreaOverlayer_2 [AREA]
AreaOnAreaOverlayer_2
    ACCUM_ATTRS_NAME = Merge Incoming Attributes
    CLEANING_TOLERANCE = Automatic
    CONNECT_Z_MODE = First Wins
    DEAGGREGATE_INPUT = Yes
    OVC_ATTR = _overlaps
    AREA -> Dissolver [off]
    AREA -> DonutBuilder
    <REJECTED> -> Inspector_2
Dissolver [off]
    ACCUM_INPUT_ATTRS = Use Attributes From One Feature
    CLEANING_TOLERANCE = Automatic
    CONNECT_Z_MODE = First Wins
    DEAGGREGATE_INPUT = Yes
    GROUP_BY = Batiment_culture_rpg Crop_rgp Forest_rpg Grass_rpg "Soil_low veg_rpg"
    AREA -> DonutBuilder [off]
DonutBuilder
    CONNECT_Z_MODE = First Wins
    DROP = no
    FLAG_ATTR = _hole_flag
    AREA -> AreaGapAndOverlapCleaner_2
AreaGapAndOverlapCleaner_2
    CLEANING_TOLERANCE = Automatic
    CONNECT_Z_MODE = First Wins
    DEAGGREGATE_INPUT = YES
    FILL_ALL_GAPS = No
    MEASURE_TYPE = Continuous
    MISSING_VAL_MODE = Compute
    REPAIR_METHOD = Longest Boundary
    REPAIRED -> Deaggregator_6
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator
AreaCalculator
    AREA_ATTR = _area_Final
    AREA_TYPE = Plane Area
    MULT = 1
    -> AttributeCreator_8
AttributeCreator_8
    ATTR_TABLE:
      SET_TO Type = FME_CONDITIONAL:DEFAULT_VALUE'_FME_NO_OP_'BOOL_OP;OR;COMPOSITE_TEST;1 OR 2;TEST @Value(Crop_rgp) = Crop_rpg;TEST @Value(Crop2) = Crop'Cropland'BOOL_OP;OR;COMPOSITE_TEST;1 OR 2;TEST @Value(Grass_rpg) = Grass_rpg ;TEST @Value(Grass2) = Grass'Grassland'BOOL_OP;OR;COMPOSITE_TEST;1 OR 2 OR 3;TEST @Value(Forest2) = Forest;TEST @Value(culture) = Vergers;TEST @Value(Forest_rpg) = 20'Forest'BOOL_OP;OR;COMPOSITE_TEST;1;TEST @Value(Wetland2) = Wetland'Wetland'BOOL_OP;OR;COMPOSITE_TEST;1 OR 2;TEST @Value(Soil_low veg_rpg) = Soil_low veg_rpg;TEST @Value(Soil_low veg2) = Soil_low veg'Soil / low veg'BOOL_OP;OR;COMPOSITE_TEST;1;TEST @Value(Water2) = Water'Water'BOOL_OP;OR;COMPOSITE_TEST;1 OR 2;TEST @Value(Batiment_culture_rpg) = Batiment_culture_rpg;TEST @Value(Other2) = Other'Other'BOOL_OP;OR;COMPOSITE_TEST;1 OR 2;TEST @Value(Crop_rgp) = Other_Crop_rpg;TEST @Value(Crop2) = Other_Crop_rpg'Other_Crop_rpg'FME_NUM_CONDITIONS9___
      SET_TO AB-LC = FME_CONDITIONAL:DEFAULT_VALUE'_FME_NO_OP_'BOOL_OP;OR;COMPOSITE_TEST;1;TEST @Value(Type) = Cropland'0'BOOL_OP;OR;COMPOSITE_TEST;1;TEST @Value(Type) = Forest'1'BOOL_OP;OR;COMPOSITE_TEST;1;TEST @Value(Type) = Grassland'2'BOOL_OP;OR;COMPOSITE_TEST;1;TEST @Value(Type) = Wetland'3'BOOL_OP;OR;COMPOSITE_TEST;1;TEST @Value(Type) = Soil / low veg'4'BOOL_OP;OR;COMPOSITE_TEST;1;TEST @Value(Type) = Water'5'BOOL_OP;OR;COMPOSITE_TEST;1;TEST @Value(Type) = Other'6'FME_NUM_CONDITIONS8___
      SET_TO Crop ID = FME_CONDITIONAL:DEFAULT_VALUE'_FME_NO_OP_'BOOL_OP;OR;COMPOSITE_TEST;1 OR 2 OR 3 OR 4 OR 5 OR 6 OR 7;TEST @Value(Crop_rgp) = BTH;TEST @Value(Crop_rgp) = BTP;TEST @Value(Crop_rgp) = BDH;TEST @Value(Crop_rgp) = BDP;TEST @Value(Crop_rgp) = BDT;TEST @Value(Crop2) = 40;TEST @Value(Crop2) = 4'0'BOOL_OP;OR;COMPOSITE_TEST;1 OR 2 OR 3 OR 4;TEST @Value(Crop_rgp) = MID;TEST @Value(Crop_rgp) = MIE;TEST @Value(Crop_rgp) = MIS;TEST @Value(Crop_rgp) = Maïs'1'BOOL_OP;OR;COMPOSITE_TEST;1 OR 2 OR 3;TEST @Value(Crop_rgp) = ORH;TEST @Value(Crop_rgp) = ORP;TEST @Value(Crop_rgp) = Orge'2'BOOL_OP;OR;COMPOSITE_TEST;1 OR 2 OR 3;TEST @Value(Crop_rgp) = CZH;TEST @Value(Crop_rgp) = CZP;TEST @Value(Crop_rgp) = Colza'3'BOOL_OP;OR;COMPOSITE_TEST;1 OR 2;TEST @Value(Crop_rgp) = SOJ;TEST @Value(Crop_rgp) = Soja'4'BOOL_OP;OR;COMPOSITE_TEST;1 OR 2;TEST @Value(Crop_rgp) = 16;TEST @Value(Crop_rgp) = Fourrage'5'BOOL_OP;OR;COMPOSITE_TEST;1;TEST @Value(Crop_rgp) = Other_Crop_rpg'6'FME_NUM_CONDITIONS8___
      SET_TO Code DW = @Value(_labelDW)
      SET_TO Code ESA = @Value(_label)
      SET_TO RPG Culture = @Value(CODE_CULTU)@Value(culture)
      SET_TO RPG Code Group = @Value(CODE_GROUP)
    -> AttributeCreator_9
AttributeCreator_9
    ATTR_TABLE:
      SET_TO Type = FME_CONDITIONAL:DEFAULT_VALUE'_FME_NO_OP_'BOOL_OP;OR;COMPOSITE_TEST;1 OR 2;TEST @Value(Crop_rgp) = Crop_rpg;TEST @Value(Crop2) = Crop'Cropland'BOOL_OP;OR;COMPOSITE_TEST;1 OR 2;TEST @Value(Grass_rpg) = Grass_rpg ;TEST @Value(Grass2) = Grass'Grassland'BOOL_OP;OR;COMPOSITE_TEST;1 OR 2 OR 3;TEST @Value(Forest2) = Forest;TEST @Value(Forest_rpg) = Vergers;TEST @Value(Forest_rpg) = 20'Forest'BOOL_OP;OR;COMPOSITE_TEST;1;TEST @Value(Wetland2) = Wetland'Wetland'BOOL_OP;OR;COMPOSITE_TEST;1 OR 2;TEST @Value(Soil_low veg_rpg) = Soil_low veg_rpg;TEST @Value(Soil_low veg2) = Soil_low veg'Soil / low veg'BOOL_OP;OR;COMPOSITE_TEST;1;TEST @Value(Water2) = Water'Water'BOOL_OP;OR;COMPOSITE_TEST;1 OR 2;TEST @Value(Batiment_culture_rpg) = Batiment_culture_rpg;TEST @Value(Other2) = Other'Other'BOOL_OP;OR;COMPOSITE_TEST;1 OR 2;TEST @Value(Crop_rgp) = Other_Crop_rpg;TEST @Value(Crop2) = Other_Crop_rpg'Other_Crop_rpg'FME_NUM_CONDITIONS9___
      SET_TO AB-LC = FME_CONDITIONAL:DEFAULT_VALUE'_FME_NO_OP_'BOOL_OP;OR;COMPOSITE_TEST;1;TEST @Value(Type) = Cropland'0'BOOL_OP;OR;COMPOSITE_TEST;1;TEST @Value(Type) = Forest'1'BOOL_OP;OR;COMPOSITE_TEST;1;TEST @Value(Type) = Grassland'2'BOOL_OP;OR;COMPOSITE_TEST;1;TEST @Value(Type) = Wetland'3'BOOL_OP;OR;COMPOSITE_TEST;1;TEST @Value(Type) = Soil / low veg'4'BOOL_OP;OR;COMPOSITE_TEST;1;TEST @Value(Type) = Water'5'BOOL_OP;OR;COMPOSITE_TEST;1;TEST @Value(Type) = Other'6'FME_NUM_CONDITIONS8___
      SET_TO Crop ID = FME_CONDITIONAL:DEFAULT_VALUE'_FME_NO_OP_'BOOL_OP;OR;COMPOSITE_TEST;1 OR 2 OR 3 OR 4 OR 5 OR 6 OR 7;TEST @Value(RPG Culture) = BTH;TEST @Value(RPG Culture) = BTP;TEST @Value(RPG Culture) = BDH;TEST @Value(RPG Culture) = BDP;TEST @Value(RPG Culture) = BDT;TEST @Value(Code ESA) = 40;TEST @Value(Code DW) = 4'0'BOOL_OP;OR;COMPOSITE_TEST;1 OR 2 OR 3 OR 4;TEST @Value(RPG Culture) = MID;TEST @Value(RPG Culture) = MIE;TEST @Value(RPG Culture) = MIS;TEST @Value(RPG Culture) = Mais'1'BOOL_OP;OR;COMPOSITE_TEST;1 OR 2 OR 3;TEST @Value(RPG Culture) = ORH;TEST @Value(RPG Culture) = ORP;TEST @Value(RPG Culture) = Orge'2'BOOL_OP;OR;COMPOSITE_TEST;1 OR 2 OR 3;TEST @Value(RPG Culture) = CZH;TEST @Value(RPG Culture) = CZP;TEST @Value(RPG Culture) = Colza'3'BOOL_OP;OR;COMPOSITE_TEST;1 OR 2;TEST @Value(RPG Culture) = SOJ;TEST @Value(RPG Culture) = Soja'4'BOOL_OP;OR;COMPOSITE_TEST;1 OR 2 OR 3;TEST @Value(RPG Culture) = 16;TEST @Value(RPG Culture) = Fourrage;TEST @Value(CODE_GROUP) = 16'5'BOOL_OP;OR;COMPOSITE_TEST;1;TEST @Value(RPG Culture) = Other_Crop_rpg'6'BOOL_OP;OR;COMPOSITE_TEST;1 OR 2;TEST @Value(Code ESA) = 10;TEST @Value(Code DW) = 1'0'BOOL_OP;OR;COMPOSITE_TEST;1;TEST @Value(RPG Culture) = Vergers'20'BOOL_OP;OR;COMPOSITE_TEST;1 OR 2 OR 3 OR 4 OR 5;TEST @Value(RPG Culture) = BFP;TEST @Value(RPG Culture) = BFS;TEST @Value(RPG Culture) = BOR;TEST @Value(RPG Culture) = BTA;TEST @Value(RPG Code Group) = 17'2'BOOL_OP;OR;COMPOSITE_TEST;1 OR 2;TEST @Value(RPG Culture) = Prairie temporaire;TEST @Value(RPG Code Group) = 19'1'BOOL_OP;OR;COMPOSITE_TEST;1 OR 2 OR 3 OR 4;TEST @Value(RPG Culture) = Prairie;TEST @Value(RPG Code Group) = 18;TEST @Value(Code ESA) = 30;TEST @Value(Code DW) = 2'0'BOOL_OP;OR;COMPOSITE_TEST;1 OR 2;TEST @Value(Code ESA) = 90;TEST @Value(Code DW) = 3'0'BOOL_OP;OR;COMPOSITE_TEST;1 OR 2 OR 3 OR 4 OR 5 OR 6 OR 7;TEST @Value(RPG Culture) = J5M;TEST @Value(RPG Culture) = J6P;TEST @Value(RPG Culture) = J6S;TEST @Value(RPG Culture) = JNO;TEST @Value(RPG Culture) = Jachere;TEST @Value(Code ESA) = 20;TEST @Value(Code DW) = 5'0'BOOL_OP;OR;COMPOSITE_TEST;1 OR 2;TEST @Value(Code ESA) = 60;TEST @Value(Code DW) = 7'1'BOOL_OP;OR;COMPOSITE_TEST;1;TEST @Value(Code ESA) = 80'0'BOOL_OP;OR;COMPOSITE_TEST;1 OR 2 OR 3 OR 4 OR 5 OR 6;TEST @Value(Code ESA) = 50;TEST @Value(Code ESA) = 70;TEST @Value(Code ESA) = 95;TEST @Value(Code ESA) = 100;TEST @Value(Code DW) = 6;TEST @Value(Code DW) = 8'0'FME_NUM_CONDITIONS18___
      SET_TO Code DW = @Value(_labelDW)
      SET_TO Code ESA = @Value(_label)
      SET_TO RPG Culture = @Value(CODE_CULTU)@Value(culture)
      SET_TO RPG Code Group = @Value(CODE_GROUP)
    -> AttributeManager_12
AttributeManager_12
    ATTR_TABLE:
      REMOVE Crop_rgp
      REMOVE Grass_rpg
      REMOVE Forest_rpg
      REMOVE Soil_low veg_rpg
      REMOVE Batiment_culture_rpg
      REMOVE CODE_GROUP
      REMOVE gc_rpg
      REMOVE CODE_CULTU
      REMOVE culture
      REMOVE _area_RPGs
      REMOVE Soil_low veg
      REMOVE Crop2
      REMOVE Forest2
      REMOVE Grass2
      REMOVE Wetland2
      REMOVE Soil_low veg2
      REMOVE Water2
      REMOVE Other2
      REMOVE _labelDW
      REMOVE _label
      REMOVE _area_LCLU
      REMOVE _area_area
      REMOVE _area_Hulle_3
      REMOVE _overlaps
      REMOVE _hole_flag
    -> Counter
Counter
    CNT_ATTR = _count
    DOMAIN = counter
    SCOPE = Global
    START = 0
    -> TestFilter_11
TestFilter_11
    DEFAULT_VALUE = <UNFILTERED>
    TEST_LIST = "BOOL_OP,OR,COMPOSITE_TEST,""""""1"""""",TEST_CLAUSE,TEST @Value(Type) = Cropland",Cropland,"BOOL_OP,OR,COMPOSITE_TEST,""""""1"""""",TEST_CLAUSE,TEST @Value(Type) = Grassland",Grassland,"BOOL_OP,OR,COMPOSITE_TEST,""""""1"""""",TEST_CLAUSE,TEST @Value(Type) = Forest",Forest,"BOOL_OP,OR,COMPOSITE_TEST,""""""1"""""",TEST_CLAUSE,TEST @Value(Type) = Soil / low veg",Soil / low veg,"BOOL_OP,OR,COMPOSITE_TEST,""""""1"""""",TEST_CLAUSE,TEST @Value(Type) = Water",Water,"BOOL_OP,OR,COMPOSITE_TEST,""""""1"""""",TEST_CLAUSE,TEST @Value(Type) = Wetland",Wetland,"BOOL_OP,OR,COMPOSITE_TEST,""""""1"""""",TEST_CLAUSE,TEST @Value(Type) = Other",Other
    Cropland -> Tester_5
    Grassland -> Tester_5
    Forest -> AreaGapAndOverlapCleaner_4
    Soil / low veg -> Tester_5
    Water -> Tester_5
    Wetland -> Tester_5
    Other -> Tester_5
    <UNFILTERED> -> Tester_5
Tester_5
    BOOL_OP = OR
    COMPOSITE_TEST = 1
    TEST_CLAUSE = TEST @Value(_area_Final) >= 100
    TEST_MODE = TEST
    PASSED -> AreaGapAndOverlapCleaner_4
AreaGapAndOverlapCleaner_4
    CLEANING_TOLERANCE = Automatic
    CONNECT_Z_MODE = First Wins
    DEAGGREGATE_INPUT = YES
    FILL_ALL_GAPS = No
    MEASURE_TYPE = Continuous
    MISSING_VAL_MODE = Compute
    REPAIR_METHOD = Longest Boundary
    REPAIRED -> SpikeRemover
    REPAIRED -> LengthCalculator_4
LengthCalculator_4
    DIM = 2
    LEN_ATTR = _length_box
    MULT = 1
    -> TestFilter_13
TestFilter_13
    DEFAULT_VALUE = <UNFILTERED>
    TEST_LIST = "BOOL_OP,OR,COMPOSITE_TEST,""""""1"""""",TEST_CLAUSE,TEST Code ESA ATTRIBUTE_HAS_A_VALUE """,ESA classes,"BOOL_OP,OR,COMPOSITE_TEST,""""""1"""""",TEST_CLAUSE,TEST Code DW ATTRIBUTE_HAS_A_VALUE """,DW classes
    ESA classes -> BoundingBoxReplacer
    DW classes -> BoundingBoxReplacer
BoundingBoxReplacer
    BBLONGER = 5
    BBSHORTER = 1
    BOXTYPE = 2D Oriented Bounding Box
    BOX -> FeatureMerger [SUPPLIER]
SpikeRemover
    DIMENSIONS = 2D
    ITERATIVE = Yes
    SPIKEANGLE = 10
    SPIKELENGTH = 250
    UNCHANGED -> AttributeManager_13
    CHANGED -> AttributeManager_13
AttributeManager_13
    ATTR_TABLE:
      REMOVE _geometry_name
      REMOVE _part_number
    -> TestFilter_12
TestFilter_12
    DEFAULT_VALUE = <UNFILTERED>
    TEST_LIST = "BOOL_OP,OR,COMPOSITE_TEST,""""""1"""""",TEST_CLAUSE,TEST Code ESA ATTRIBUTE_HAS_A_VALUE """,ESA classes,"BOOL_OP,OR,COMPOSITE_TEST,""""""1"""""",TEST_CLAUSE,TEST Code DW ATTRIBUTE_HAS_A_VALUE """,DW classes
    ESA classes -> Junction_7
    DW classes -> Junction_7
    <UNFILTERED> -> Junction_3
Junction_7
    -> LengthCalculator_2
    -> LengthCalculator_3
    -> FeatureMerger [REQUESTOR]
FeatureMerger
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> AttributeManager_15
    UNMERGED_REQUESTOR -> AttributeManager_15
AttributeManager_15
    ATTR_TABLE:
      REMOVE _geometry_name
      REMOVE _part_number
      SET_TO R_Short2Long_side = @Evaluate(@Value(1)/@Value(5))
    USER_EXPOSED_ATTRIBUTES = Area
    -> AttributeRounder_3
AttributeRounder_3
    PLACES = 1
    ROUND_TYPE = Nearest
    SRC_ATTRS = R_Short2Long_side
    -> AttributeManager_18
AttributeManager_18
    NUM_PRIOR_FEATURES = 0
    NUM_SUBSEQUENT_FEATURES = 0
    -> Junction_3
LengthCalculator_2
    DIM = 2
    LEN_ATTR = ESA_length
    MULT = 1
    -> AttributeManager
AttributeManager
    ATTR_TABLE = SET_TO RATIO_P_A = @Evaluate(@Value(ESA_length)/@Value(_area_Final)*1)
    -> AttributeRounder
AttributeRounder
    PLACES = 1
    ROUND_TYPE = Nearest
    SRC_ATTRS = RATIO_P_A
    -> Junction_3
LengthCalculator_3
    DIM = 2
    LEN_ATTR = DW_length
    MULT = 1
    -> AttributeManager_2
AttributeManager_2
    ATTR_TABLE = SET_TO DW_Ratio peri = @Evaluate(@Value(DW_length)/@Value(_area_Final))
    USER_EXPOSED_ATTRIBUTES = Area
    -> AttributeRounder_2
AttributeRounder_2
    PLACES = 1
    ROUND_TYPE = Nearest
    SRC_ATTRS = DW_Ratio peri
    -> Junction_3
Junction_3
    -> AttributeManager_16
AttributeManager_16
    -> TestFilter_14
TestFilter_14
    DEFAULT_VALUE = <UNFILTERED>
    TEST_LIST:
      "BOOL_OP,OR,COMPOSITE_TEST,""""""1 OR 2"""""",TEST_CLAUSE,TEST Code ESA ATTRIBUTE_HAS_A_VALUE ""
      TEST Code DW ATTRIBUTE_HAS_A_VALUE """,ESA_DW
    ESA_DW -> Tester_7
    <UNFILTERED> -> AttributeManager_14
Tester_7
    BOOL_OP = AND
    COMPOSITE_TEST = 1 AND 2
    TEST_CLAUSE:
      TEST @Value(R_Short2Long_side) <= 0.1
      TEST @Value(_area_Final) <= 1000
    TEST_MODE = TEST
    FAILED -> LengthCalculator_5
LengthCalculator_5
    DIM = 2
    LEN_ATTR = _length_Final
    MULT = 1
    -> Tester_14
Tester_14
    BOOL_OP = COMPOSITE
    COMPOSITE_TEST = 1 AND 2
    TEST_CLAUSE:
      TEST @Value(R_Short2Long_side) = 0
      TEST @Value(_length_Final) <= 500
    TEST_MODE = TEST
    FAILED -> AttributeManager_14
AttributeManager_14
    ATTR_TABLE:
      RENAME_SET_VALUE _count > ID
      RENAME_SET_VALUE R_Short2Long_side > Lines_Ratio
      RENAME_SET_VALUE _length_Final > Lenght
      RENAME_SET_VALUE _circularity_Final > Circularity
      RENAME_SET_VALUE _area_Final > Area
      REMOVE DW_length
      REMOVE DW_Ratio peri
      REMOVE ESA_length
      REMOVE RATIO_P_A
      REMOVE _hierarchy_child_id_list{}
      REMOVE _hierarchy_id
      REMOVE _hierarchy_parent_id
      REMOVE _area_cleaning
      REMOVE _length_box
      REMOVE 5
      REMOVE 1
      REMOVE _area_circular
      REMOVE _circularityyyyyy
      REMOVE _areaaaaaaaaaaa
      REMOVE _circularity
    -> Junction_8
Junction_8
    -> Reprojector_5
    -> HomogenAreas (writer SHAPEFILE_6)
Reprojector_5
    DEST = EPSG:2154
    INTERPOLATION_TYPE_NAME = Nearest Neighbor
    RASTER_CELL_SIZE = Preserve Cells
    RASTER_TOLERANCE = 0.0
    REPROJECTED -> GeometryCoercer
GeometryCoercer
    GQUERY:
      for $geom in //geometry
      where $geom/count(parent::geometry) = 0
      return number($geom/@fme_id)
    KIND = fme_line
    COERCED -> LengthCalculator
LengthCalculator
    DIM = 2
    LEN_ATTR = _length
    MULT = 1
    -> TestFilter_8
TestFilter_8
    DEFAULT_VALUE = <UNFILTERED>
    TEST_LIST = "BOOL_OP,OR,COMPOSITE_TEST,""""""1"""""",TEST_CLAUSE,TEST @Value(_length) >= 1000",1000 meter,"BOOL_OP,OR,COMPOSITE_TEST,""""""1"""""",TEST_CLAUSE,TEST @Value(_length) >= 500",500 meter,"BOOL_OP,OR,COMPOSITE_TEST,""""""1"""""",TEST_CLAUSE,TEST @Value(_length) >= 100",100 meter,"BOOL_OP,OR,COMPOSITE_TEST,""""""1"""""",TEST_CLAUSE,TEST @Value(_length) >= 50",50 meter,"BOOL_OP,OR,COMPOSITE_TEST,""""""1"""""",TEST_CLAUSE,TEST @Value(_length) <= 50",- 50 meter
    1000 meter -> IterativeSnipper
    500 meter -> IterativeSnipper_4
    100 meter -> IterativeSnipper_2
    50 meter -> IterativeSnipper_3
    - 50 meter -> Bufferer
IterativeSnipper
    DOMAIN = Divide_Line
    SNIPMODE = ToNumber
    SnipLength = 10
    -> Bufferer
IterativeSnipper_4
    DOMAIN = Divide_Line
    SNIPMODE = ToNumber
    SnipLength = 5
    -> Bufferer
IterativeSnipper_2
    DOMAIN = Divide_Line
    SNIPMODE = ToNumber
    SnipLength = 3
    -> Bufferer
IterativeSnipper_3
    DOMAIN = Divide_Line
    SNIPMODE = ToNumber
    SnipLength = 2
    -> Bufferer
Bufferer
    ANGLE = 22.5
    CAP_STYLE = Arc
    CORNER_STYLE = Arc
    MODE = AREA
    OFFSET = 5
    OFFSET_UNITS = NONE
    PRECISION = APPROX
    BUFFERED -> Inspector
    BUFFERED -> AttributeManager_17
Inspector
AttributeManager_17
    -> Line_Poly (writer SHAPEFILE_7)
Line_Poly (writer SHAPEFILE_7)
    attributes: Type varchar(200), AB_LC varchar(200), Crop_ID varchar(200), Code_DW varchar(254), ID number(20,0), Code_ESA varchar(254), RPG_Cultur varchar(200), RPG_Code_G varchar(2), Area double, Lines_Rati varchar(200), Lenght double, Circularit double, SegmentNum number(20,0), _length double
HomogenAreas (writer SHAPEFILE_6)
    attributes: ID number(20,0), Type varchar(200), AB_LC varchar(200), Crop_ID varchar(200), Code_DW varchar(254), Code_ESA varchar(254), RPG_Cultur varchar(200), RPG_Code_G varchar(2), Lines_Rati varchar(200), Lenght double, Circularit double, Area double
Inspector_2

Bookmark: Transport Networks/ IGN, OSM
Transport_Routiere_Network (reader SHAPEFILE_4) [off]
    attributes: ID_RTE500 varchar(24), VOCATION varchar(80), NB_CHAUSSE varchar(80), NB_VOIES varchar(80), ETAT varchar(80), ACCES varchar(80), RES_VERT varchar(80), SENS varchar(80), NUM_ROUTE varchar(24), RES_EUROPE varchar(200), LONGUEUR float, CLASS_ADM varchar(20)
    -> Reprojector_6 [off]
Reprojector_6 [off]
    DEST = EPSG:2154
    INTERPOLATION_TYPE_NAME = Nearest Neighbor
    RASTER_CELL_SIZE = Preserve Cells
    RASTER_TOLERANCE = 0.0
    REPROJECTED -> TestFilter_2 [off]
TestFilter_2 [off]
    DEFAULT_VALUE = Departementale
    TEST_LIST = "BOOL_OP,OR,COMPOSITE_TEST,""""""1"""""",TEST_CLAUSE,TEST @Value(CLASS_ADM) = Autoroute",Autoroute,"BOOL_OP,OR,COMPOSITE_TEST,""""""1"""""",TEST_CLAUSE,TEST @Value(CLASS_ADM) = Nationale",National,"BOOL_OP,OR,COMPOSITE_TEST,""""""1"""""",TEST_CLAUSE,TEST @Value(CLASS_ADM) = Sans objet",Other
    Autoroute -> Bufferer_2 [off]
    National -> Bufferer_4 [off]
    Other -> Bufferer_6 [off]
    Departementale -> Bufferer_8 [off]
Bufferer_2 [off]
    ANGLE = 22.5
    CAP_STYLE = Arc
    CORNER_STYLE = Arc
    MODE = AREA
    OFFSET = 10
    OFFSET_UNITS = METERS
    PRECISION = APPROX
    BUFFERED -> Junction_2
Bufferer_4 [off]
    ANGLE = 22.5
    CAP_STYLE = Arc
    CORNER_STYLE = Arc
    MODE = AREA
    OFFSET = 7
    OFFSET_UNITS = METERS
    PRECISION = APPROX
    BUFFERED -> Junction_2
Bufferer_6 [off]
    ANGLE = 22.5
    CAP_STYLE = Arc
    CORNER_STYLE = Arc
    MODE = AREA
    OFFSET = 3
    OFFSET_UNITS = METERS
    PRECISION = APPROX
    BUFFERED -> Junction_2
Bufferer_8 [off]
    ANGLE = 22.5
    CAP_STYLE = Arc
    CORNER_STYLE = Arc
    MODE = AREA
    OFFSET = 6
    OFFSET_UNITS = METERS
    PRECISION = APPROX
    BUFFERED -> Junction_2
railways (reader SHAPEFILE_3)
    attributes: osm_id number(11,0), name varchar(48), type varchar(16)
    -> AttributeCreator
AttributeCreator
    ATTR_TABLE = SET_TO Railway = @Value(type)
    -> Bufferer_10
Bufferer_10
    ANGLE = 22.5
    CAP_STYLE = Arc
    CORNER_STYLE = Arc
    MODE = AREA
    OFFSET = 2.5
    OFFSET_UNITS = METERS
    PRECISION = APPROX
    BUFFERED -> Junction_2
subway_osm (reader GEOJSON_1)
    attributes: full_id string, osm_id string, osm_type string, route string, crossing:markings string, name:zh string, deck string, payment:via_verde:lanes string, railway:interlaced string, ship string, motorboat string, canoe string, boat string, via_ferrata_scale string, rungs string, safety_rope string, assisted_trail string, bicycle:left string, bicycle:forward string, ref:refuges.info string, departures_board string, narrow string, ref:2010 string, destination:ref:lanes:forward string, destination:lanes:forward string, razed:railway string, overhang string, ladder string, minspeed:lanes:backward string, parking:condition:left:residents string,
      parking:lane:left:diagonal string, material string, bicycle:backward string, cycleway:surface:colour string, link string, roller_coaster string, leisure string, attraction string, maxspeed:source string, lanes:both_ways string, vehicle:lanes:forward string, vehicle:lanes:backward string, motorhome string, parking:right:zone string, parking:right:markings string, parking:left:restriction string, parking:left:reason string, temporary:access string, check_date string, turn:backward string, cycleway:lanes:backward string, source:url string, source:bus_bay string, destination:symbol:forward string, destination:ref:forward string, maxspeed:lanes:backward string, note:destination string, source:name:ca string, bus:lanes:forward string, ref:kgs string,
      source:bridge:name string, maxweightrating string, transit:lanes string, source:destination:date string, stroller string, source:destination string, turn:forward string, placement:forward string, surface:note string, maxweight:forward:conditional string, ramp string, handrail string, noexit string, lanes:-2023 string, mtb:name string, check_date:cycleway string, placement:start string, piste:name string, maxspeed:hgv:lanes string, sac_scale_ref string, access:winter string, sport string, phone string, border_type string, cycleway:oneway string, abandoned:highway string, duration string, path string, maxspeed:recommended:forward string, source:incline string,
      name:de string, footway string, avalanche_protector:left string, minspeed:lanes:forward string, name:en string, network:wikidata string, maxspeed:caravan string, destination:colour:backward string, psv:lanes:forward string, access:lanes:forward string, parking:lane string, name:wikipedia string, arcade:right string, cycleway:left:width string, mtb:type string, class:bicycle:mtb string, parking:lane:left:capacity string, man_made string, 4wd_only string, sidewalk:both:wheelchair string, name:tr string, name:ru string, shelter string, bin string, bench string, turn string, mtb string, historic:civilization string, waterway string, route_ref string,
      public_transport string, note:route_ref string, tree_row string, placement:backward string, hiking string, destination:ref:backward string, comment string, placement:both_ways string, maxspeed:lanes:forward string, historic string, shoulder:left string, description:es string, maxheight:forward string, oneway:hgv string, abandoned string, network string, placement:end string, cycleway:width string, cycleway:buffer string, was:lanes string, traffic_sign:backward string, horse_scale string, sidewalk:right:bicycle string, parking:condition:right:customers string, side string, overtaking:backward string, bus_bay string, bridge:name:oc string, bridge:name:ca string, priority string,
      footway:right:wheelchair string, footway:left:wheelchair string, operator:wikipedia string, operator:wikidata string, circuits string, cables string, substation string, ref:FR:RTE_nom string, ref:FR:RTE string, power string, barrier string, destination:colour:forward string, cycleway:both:segregated string, max string, oneway:bus string, tourism string, mtb:scale:imba string, source:imagery string, motor_vehicle:lanes string, piste:oneway string, piste:difficulty string, old_name:fr string, lcn string, ref:MMM string, maxspeed:recommended:backward string, lanes:bus:forward string, source:width string, recommended_speed string, piste:type string, piste:grooming string,
      maxwidth string, services string, residents string, int_name string, source:name:br:date string, speed string, type string, goods string, source:bridge string, alt_name:es string, parking:lane:both:capacity string, parking:condition:both:time_interval string, parking:condition:both:maxstay string, parking:condition:both:fee_per_hour string, parking:condition:both:default string, parking:condition:both:3:residents string, parking:condition:both:3:maxstay string, parking:condition:both:3 string, parking:condition:both:2:time_interval string, parking:condition:both:2:maxstay string, parking:condition:both:2:fee_per_hour string, parking:condition:both:2 string, lanes:psv:backward string, height string, check_date:surface string, proposed_ref string, historic:start_date string, historic:gauge string, historic:end_date string, historic:electrified string,
      name:ja string, bridge:name:nl string, bridge:name:fr string, bridge:name:en string, maxwidth:physical string, note:FR string, construction string, maxheight:lanes string, smoothness:date string, parking:right:fee string, parking:right:orientation string, motorhome:conditional string, trailblazed string, osmc:symbol string, ford string, cycleway:right:oneway string, cycleway:lane string, step_count string, viaduct:name string, bus:lanes:backward string, access:lanes:backward string, parking:lane:right:access string, maxaxleload string, psv:lanes:backward string, source:cycleway string, ref:MEL string, brp_access string, note:voltage string, disused:railway string, overtaking:goods string,
      note:service string, railway:preserved string, trail_visibility string, long_name string, source:hazard string, postal_code string, minspeed:lanes string, maxspeed:psv string, hgv:lanes string, cycleway:right:width string, traffic_sign string, source:heritage string, ref:mhs string, railway:scmt string, railway:ptc string, railway:etcs string, railway:atb string, mhs:inscription_date string, heritage:operator string, heritage string, bridge:wikipedia string, cycleway:right:segregated string, location string, cutting:right string, animal_crossing string, old:maxspeed string, parking:lane:left:parallel string, lanes:reversible string, bridge:ref string, mtb:scale:uphill string,
      mtb:scale string, bridge:movable string, tactile_paving string, segregated string, footway:surface string, cycleway:surface string, crossing:island string, crossing string, motorcycle:conditional string, motorcar:conditional string, motor_vehicle:conditional string, maxlength string, abandoned:railway string, inscription string, ref:FFRP string, sidewalk:left:bicycle string, length string, source:lanes string, source:maxheight string, shoulder:width string, note:fr string, hazard:animal string, maxspeed:backward string, old_name:eu string, old_name:es string, date string, check_date:lit string, sidewalk:bicycle string, bridge:name:es string, construction:railway:etcs string,
      wikimedia_commons string, maxspeed:advisory string, tunnel:length string, overtaking:forward string, ele string, change:lanes:forward string, change:lanes:backward string, noref string, rcrc_ref string, snowmobile string, ski string, maxspeed:forward string, source:geometry string, architect:wikidata string, architect string, local_ref string, website string, source:pkey string, source:description string, cycleway:left:oneway string, destination:int_ref:lanes string, highway:2021-11-05 string, access:2021-11-05 string, turn:bus:lanes:backward string, lanes:bus:backward string, hgv:forward string, hgv:backward string, hgv string, alt_name:ca string, source:highway string,
      maxweight:conditional string, traffic_calming string, sidewalk:right:surface string, sidewalk:left:surface string, parking string, psv:lanes string, service string, note:en string, hgv:conditional string, class:bicycle string, signals string, tunnel:name:es string, tunnel:name:en string, tunnel:name:ca string, destination:nat_ref string, ref:tunnel string, mindistance:hgv string, mindistance string, overtaking:hgv string, source:ref string, source:name string, destination:symbol:lanes string, destination:colour:lanes string, parking:condition:left string, official_ref string, motorcar string, reg_ref string, description string, parking:both:zone string, parking:both:markings string,
      parking:both:fee string, destination:forward string, destination:backward string, parking:both:reason string, parking:right:restriction string, parking:right string, parking:left:zone string, parking:left:orientation string, parking:left:fee string, parking:left string, name:etymology:wikipedia string, change:lanes string, sidewalk:both:surface string, taxi string, psv string, parking_lane string, level string, parking:both:restriction string, destination:symbol:backward string, destination:lanes:backward string, zone:traffic string, destination:ref:to:lanes string, tracktype string, bridge:structure string, cycleway:left:lane string, wheelchair string, admin_level string, destination:lang:es string, width string, maxweight string,
      lanes:psv:forward string, cs_dir:backward string, oneway:psv string, cycleway:right:lane string, busway:left string, ref:FR:SNCF_Reseau:GAIA string, source:date string, official_name string, moped string, mofa string, access string, toll:2021-08-31 string, name:ca string, lanes:bus string, maxweight:signed string, source:lit string, grande_circulation string, parking:lane:right:parallel string, parking:lane:right:capacity string, parking:lane:right string, parking:lane:left string, parking:condition:right:time_interval string, parking:condition:right:maxstay string, parking:condition:right:fee_per_hour string, parking:condition:right:default string, parking:condition:right:3:residents string, parking:condition:right:3:maxstay string, parking:condition:right:3 string, parking:condition:right:2:time_interval string, parking:condition:right:2:maxstay string,
      parking:condition:right:2:fee_per_hour string, parking:condition:right:2 string, parking:condition:right string, oneway:bicycle string, motor_vehicle:lanes:forward string, incline string, bicycle:lanes:forward string, turn:lanes:backward string, motor_vehicle:lanes:backward string, cycleway:both:lane string, bicycle:lanes:backward string, railway:tvm string, highspeed string, overtaking string, hazmat string, destination:to string, cutting string, hazmat:E string, maxspeed:lanes string, trolley_wire string, sidewalk:right string, sidewalk:left string, ref:colour_tx string, name:eu string, name:es string, hazard string, guard_rail string, maxspeed:variable string, parking:lane:both:parallel string, destination:ref:to string,
      covered string, ref:colour string, sidewalk:both string, owner string, ssvz string, maxspeed:conditional string, old_name string, maxspeed:hgv:conditional string, bridge:name string, ref:FR:FANTOIR string, image string, source:name:br string, name:br string, motorcycle string, embankment:right string, agricultural string, maxspeed:trailer string, overtaking:hgv:conditional string, embankment string, direction string, junction:ref string, parking:both:orientation string, parking:both string, zone:maxspeed string, noname string, junction string, wikipedia string, wikidata string, turn:lanes:forward string, lanes:forward string,
      lanes:backward string, cycleway:left string, cycleway string, taxi:lanes string, busway string, bus:lanes string, access:lanes string, vehicle string, parking:condition:both string, name:etymology:wikidata string, motor_vehicle string, bus string, slow_moving string, maxspeed:hgv string, maxspeed:bus string, minspeed string, dual_carriageway string, tunnel:name string, tunnel string, destination:int_ref string, destination:ref string, turn:lanes string, cs_dir:forward string, avz string, voltage string, usage string, ref:FR:SNCF_Reseau string, railway:traffic_mode string, railway:track_ref string, railway:radio string,
      railway:preferred_direction string, railway:kvb string, railway:bidirectional string, railway string, passenger_lines string, loading_gauge string, importance string, gauge string, frequency string, electrified string, survey:date string, ref:FR:commune string, parking:lane:both string, maxweight:lanes string, mapillary string, lanes:psv string, start_date string, short_name string, destination:ref:lanes string, placement string, toll:hgv string, old_ref string, cycleway:both string, destination:lanes string, stopping string, loc_ref string, name:nl string, nat_ref string, loc_name string, sac_scale string,
      horse string, source:name:oc string, source:maxspeed string, smoothness string, shoulder:right string, name:oc string, name:fr string, operator string, shoulder string, alt_name string, layer string, int_ref string, bridge string, destination:symbol string, destination:colour string, toll string, ref string, maxheight string, foot string, bicycle string, maxspeed:type string, lane_markings string, motorroad string, destination string, sidewalk string, lit string, lanes string, busway:right string, surface string, political_division string,
      oneway string, name string, maxspeed string, highway string, cycleway:right string, boundary string
    -> AttributeCreator_2
AttributeCreator_2
    ATTR_TABLE = SET_TO OSM_way = @Value(osm_type)
    -> Bufferer_3
Bufferer_3
    ANGLE = 22.5
    CAP_STYLE = Arc
    CORNER_STYLE = Arc
    MODE = AREA
    OFFSET = 2
    OFFSET_UNITS = METERS
    PRECISION = APPROX
    BUFFERED -> Junction_2
route (reader OGCGEOPACKAGE_1)
    attributes: full_id text, osm_id text, osm_type text, route text, sac_scale_ref text, check_date text, rating text, max:abseil text, old_name:oc text, name:pt text, noname text, alt_ref text, network:type text, tourism text, attraction text, name:it text, sac_scale text, cables text, pilgrimage text, is_in text, ref:FR:RTE text, highspeed text, colour:text text, ref:onvvv text, symbol:fr text, state text, proposed:route text, ref:FR:aec31 text, piste:type text, hiking text,
      source:colour text, sleeping text, proposed text, air_conditioning text, note:network text, phone text, old_network text, operator:wikipedia text, descent text, ascent text, duration text, url text, name:es text, name:de text, name:bg text, voltage text, usage text, passenger_lines text, name:pl text, gauge text, frequency text, electrified text, operator:wikidata text, osmc:ref text, alt_name text, name:eu text, wheelchair text, service text, by_night text, bicycle text,
      roundtrip text, osmc:symbol text, distance text, website text, via text, reservation text, network:wikipedia text, network:wikidata text, fee text, comment text, colour text, public_transport:version text, operator text, old_ref text, old_name text, description text, symbol text, source:name:oc text, name:oc text, wikipedia text, network text, name:sk text, name:nl text, name:fr text, name:en text, name:cs text, name:ca text, e-road:class text, description:fr text, wikidata text,
      type text, to text, ref text, name text, from text, fid int,PrimaryKey
    -> AttributeCreator_3
AttributeCreator_3
    ATTR_TABLE = SET_TO OSM_route = @Value(route)
    -> Bufferer_5
Bufferer_5
    ANGLE = 22.5
    CAP_STYLE = Arc
    CORNER_STYLE = Arc
    MODE = AREA
    OFFSET = 4
    OFFSET_UNITS = METERS
    PRECISION = APPROX
    BUFFERED -> Junction_2
Waterway_OSM (reader GEOJSON_2)
    attributes: full_id string, osm_id string, osm_type string, waterway string, whitewater:section_name string, route string, architect string, level string, ele string, loc_name string, structure_gauge string, start_date string, lit string, seamark:gate:category string, diameter string, culvert string, ref:name string, name:right string, name:left string, name:alt string, irrigation string, surface string, ship string, canoe string, image string, name:ru string, source:date string, maxheight:marine string, seasonal string, description string,
      flow_direction string, type string, operator:wikidata string, comment string, embankment string, source:2:url string, source:2 string, covered string, access string, highway string, source:ref:sandre string, material string, source:name string, source:maxspeed string, note:maxspeed string, seamark:type string, lock:height string, self_service string, automated string, historic string, old_name string, maxspeed string, disused:admin_level string, substance string, man_made string, location string, whitewater:section_grade string, source:heritage string, ref:mhs string, mhs:inscription_date string,
      heritage:operator string, heritage string, bridge:name string, passage_time string, lock_ref string, lock_name string, lock string, nudism string, name:hu string, source:imagery string, disused string, border_type string, usage string, source_ref string, ref string, alt_name string, maxheight string, ref:sandre string, operator string, wikipedia string, tunnel:name string, tunnel string, name:es string, width string, tidal string, layer string, bridge string, wikidata string, intermittent string, name:ca string,
      political_division string, name:fr string, boundary string, admin_level string, source:name:oc string, short_name string, name:oc string, name string, motorboat string, boat string, CEMT string
    -> AttributeCreator_4
AttributeCreator_4
    ATTR_TABLE = SET_TO OSM_Waterway = @Value(waterway)
    -> TestFilter_5
TestFilter_5
    DEFAULT_VALUE = <UNFILTERED>
    TEST_LIST = "BOOL_OP,OR,COMPOSITE_TEST,""""""1"""""",TEST_CLAUSE,TEST @Value(OSM_Waterway) = drain",Drain,"BOOL_OP,OR,COMPOSITE_TEST,""""""1"""""",TEST_CLAUSE,TEST @Value(OSM_Waterway) = river",River
    Drain -> Bufferer_7
    River -> Bufferer_9
Bufferer_7
    ANGLE = 22.5
    CAP_STYLE = Arc
    CORNER_STYLE = Arc
    MODE = AREA
    OFFSET = 1.5
    OFFSET_UNITS = METERS
    PRECISION = APPROX
    BUFFERED -> Junction_2
Bufferer_9
    ANGLE = 22.5
    CAP_STYLE = Arc
    CORNER_STYLE = Arc
    MODE = AREA
    OFFSET = 5
    OFFSET_UNITS = METERS
    PRECISION = APPROX
    BUFFERED -> Junction_2
Hydrographique_Network (reader SHAPEFILE_5) [off]
    attributes: LARGEUR varchar(25), TOPONYME varchar(80)
    -> Reprojector_7 [off]
Reprojector_7 [off]
    DEST = EPSG:2154
    INTERPOLATION_TYPE_NAME = Nearest Neighbor
    RASTER_CELL_SIZE = Preserve Cells
    RASTER_TOLERANCE = 0.0
    REPROJECTED -> Bufferer_12 [off]
Bufferer_12 [off]
    ANGLE = 22.5
    CAP_STYLE = Arc
    CORNER_STYLE = Arc
    MODE = AREA
    OFFSET = 3
    OFFSET_UNITS = METERS
    PRECISION = APPROX
    BUFFERED -> Junction_2 [off]
Junction_2
    -> AttributeManager_3

Bookmark: Tile & RPG + completed RPG
id_74 (reader OGCGEOPACKAGE_4)
    attributes: id double, left double, top double, right double, bottom double, fid int,PrimaryKey
    -> Reprojector
Reprojector
    DEST = EPSG:2154
    INTERPOLATION_TYPE_NAME = Nearest Neighbor
    RASTER_CELL_SIZE = Preserve Cells
    RASTER_TOLERANCE = 0.0
    REPROJECTED -> Clipper_3 [CLIPPER]
PARCELLES_GRAPHIQUES (reader SHAPEFILE_2)
    attributes: ID_PARCEL varchar(10), SURF_PARC float, CODE_CULTU varchar(3), CODE_GROUP varchar(2), CULTURE_D1 varchar(3), CULTURE_D2 varchar(3)
    -> Junction
rpg_complete_2020_d09 (reader SHAPEFILE_1)
    attributes: id_parc varchar(23), surf_ha double, surf_m2 double, culture varchar(18), gc_rpg varchar(6), proba varchar(5), com_insee varchar(9), code_pra varchar(8), rpg19_gpe varchar(9), rpg19_cult varchar(10), rpg18_gpe varchar(9), rpg18_cult varchar(10), rpg17_gpe varchar(9), rpg17_cult varchar(10), rpg16_gpe varchar(9), rpg16_cult varchar(10), rpg15_gpe varchar(9), rpg15_cult varchar(10)
    -> Junction
Junction
    -> Reprojector_2
Reprojector_2
    DEST = EPSG:2154
    INTERPOLATION_TYPE_NAME = Nearest Neighbor
    RASTER_CELL_SIZE = Preserve Cells
    RASTER_TOLERANCE = 0.0
    REPROJECTED -> Junction_6

Bookmark: ESA & Dynamic World land cover
GEOTIFF (reader GEOTIFF_2)
    -> Reprojector_4
Reprojector_4
    DEST = EPSG:2154
    INTERPOLATION_TYPE_NAME = Nearest Neighbor
    RASTER_CELL_SIZE = Preserve Cells
    RASTER_TOLERANCE = 0.0
    REPROJECTED -> RasterToPolygonCoercer_2
RasterToPolygonCoercer_2
    EXTRACT_NODATA = No
    LABEL_ATTRIBUTE = _labelDW
    PRESERVE_ATTRIBUTES = Yes
    POLYGONS -> AreaCalculator_3
AreaCalculator_3
    AREA_ATTR = _area
    AREA_TYPE = Plane Area
    MULT = 1
    -> Tester_3
Tester_3
    BOOL_OP = OR
    COMPOSITE_TEST = 1
    TEST_CLAUSE = TEST @Value(_area) >= 1000
    TEST_MODE = TEST
    PASSED -> Aggregator_6
GEOTIFF (reader GEOTIFF_1)
    attributes: product_grid char(255), copyright char(255), creation_time char(255), algorithm_version char(255), license char(255), product_tile char(255), title char(255), product_type char(255), reference char(255), time_start char(255), legend char(255), time_end char(255), product_version char(255), product_crs char(255)
    -> Reprojector_3
Reprojector_3
    DEST = EPSG:2154
    INTERPOLATION_TYPE_NAME = Nearest Neighbor
    RASTER_CELL_SIZE = Preserve Cells
    RASTER_TOLERANCE = 0.0
    REPROJECTED -> RasterToPolygonCoercer
RasterToPolygonCoercer
    EXTRACT_NODATA = No
    LABEL_ATTRIBUTE = _label
    PRESERVE_ATTRIBUTES = Yes
    POLYGONS -> AreaCalculator_2
AreaCalculator_2
    AREA_ATTR = _area
    AREA_TYPE = Plane Area
    MULT = 1
    -> Tester
Tester
    BOOL_OP = OR
    COMPOSITE_TEST = 1
    TEST_CLAUSE = TEST @Value(_area) >= 1000
    TEST_MODE = TEST
    PASSED -> Aggregator_2

FME custom transformer SmartCleaner_2013
SmartCleaner adds two new capabilities to the Intersector - extending undershot lines to intersection and deleting overshoots shorter than a specified length. 
Both the undershoot and overshoot tolerances may be taken from a feature attribute or a keyin. This transformer works only on lines, all other features are sent to the <REJECTED> port.
See http://knowledge.safe.com/articles/How_To/Example-of-the-SmartCleaner-Custom-Transformer for more information.
The transformer has two parameters:
    Extension Length:
The distance to extend undershot lines in order to intersect another line.
    Overshoot Length:
The minimum length a dangling line must be in order to be retained.

Parameters:
- LEN =
- VAL =

INPUT (input)
    -> GeometryFilter
Note: Route any non-line features / to rejected port
GeometryFilter
    BREAK_AGG = No
    POINT -> <REJECTED> (output)
    LINE -> GeometryValidator
    ARC -> <REJECTED> (output)
    AREA -> <REJECTED> (output)
    ELLIPSE -> <REJECTED> (output)
    TEXT -> <REJECTED> (output)
    RASTER -> <REJECTED> (output)
    POINTCLOUD -> <REJECTED> (output)
    SURFACE -> <REJECTED> (output)
    SOLID -> <REJECTED> (output)
    COLLECTION -> <REJECTED> (output)
    NULL -> <REJECTED> (output)
    INSTANCE -> <REJECTED> (output)
Note: Fix geometry problems
GeometryValidator
    ARC_ENDPOINT_TOLERANCE_MODE = Auto
    CHECK_HOLE_TOUCHING_POLYGON = No
    CONSECUTIVE_IDENTICAL_VERTICES_2D = CONSECUTIVE_IDENTICAL_VERTICES_2D
    DUP_COORDS_CHECK_Z = No
    MISSING_TEXTURE_COORDINATES = MISSING_TEXTURE_COORDINATES
    MISSING_VERTEX_NORMALS = MISSING_VERTEX_NORMALS
    NAN_REMOVAL = NAN_REMOVAL
    NULL_REMOVAL = NULL_REMOVAL
    OGC_SIMPLE_CHECK = OGC_SIMPLE_CHECK
    OGC_VALID_CHECK = OGC_VALID_CHECK
    PLANAR_SURFACE = PLANAR_SURFACE
    PLANAR_TOLERANCE_MODE = Auto
    PRESETS = All
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%MISSING_VERTEX_NORMALS%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"
    SELF_INTERSECTING = SELF_INTERSECTING
    SHELL_VALIDATION = SHELL_VALIDATION
    SOLID_VOID_REPAIR = SOLID_VOID_REPAIR
    TYPE_REPAIR = TYPE_REPAIR
    PASSED -> Intersector
    FAILED -> Intersector
    REPAIRED -> Intersector
Note: Intersect lines
Intersector
    DUPLICATE_Z_NODES = No
    OV_ATTR = _overlaps
    PERFORM_SELF_INTERSECTION = No
    SEG_ATTR = _segments
    SEPARATE_COLLINEAR_SEGMENTS = No
    INTERSECTED -> TopologyBuilder [LINE]
Note: Create node/line / topology to query
TopologyBuilder
    ALLOW_CYCLES = No
    ALL_EDGES = Yes
    CLEAN_DATA = Yes
    MAX = 0
    OVERLAPPING_MODE = No
    PROP_ATTRS = No
    LINE -> Cloner
    LINE -> TestFilter_2
Note: Find dangling lines to extend
TestFilter_2
    DEFAULT_VALUE = <UNFILTERED>
    TEST_LIST:
      BOOL_OP,AND,COMPOSITE_TEST,<Unused>,TEST_CLAUSE,"TEST @Evaluate(abs(@Value(_right_edge))) = @Value(_arc_id)
      TEST @Evaluate(abs(@Value(_left_edge))) = @Value(_arc_id)",BOTH,BOOL_OP,AND,COMPOSITE_TEST,<Unused>,TEST_CLAUSE,"TEST @Evaluate(abs(@Value(_left_edge))) = @Value(_arc_id)",BEGINNING,BOOL_OP,AND,COMPOSITE_TEST,<Unused>,TEST_CLAUSE,"TEST @Evaluate(abs(@Value(_right_edge))) = @Value(_arc_id)",END
    BOTH -> Extender
    BOTH -> Extender_2
    BEGINNING -> Extender
    END -> Extender_2
Note: Attached to other lines only / at the end, so extend start / of line
Extender
    LEN = $(LEN)
    NUM_SEGS = 1
    BEGINNING -> AttributeCreator_2
Note: Attached to other lines only / at the start, so extend end / of line
Extender_2
    LEN = $(LEN)
    NUM_SEGS = 1
    END -> AttributeCreator_2
Note: Flag extensions for / future cleanup
AttributeCreator_2
    ATTR_LIST = _smartcleaner_extended,1
    -> AttributeRemover_3
Note: Attached at both / ends, so no extension
Cloner
    COPIES = 1
    COPYATT = _copynum
    COPY -> AttributeRemover_3
Note: Clean up unneeded / attributes
AttributeRemover_3
    REMOVE_ATTRS = _overlaps,_segments,_arc_id,_right_polygon,_left_polygon,_right_edge,_left_edge,_from_node,_to_node,_polygons,_copynum
    -> GeometryValidator_2
Note: Fix geometry problems
GeometryValidator_2
    ARC_ENDPOINT_TOLERANCE_MODE = Auto
    CHECK_HOLE_TOUCHING_POLYGON = No
    CONSECUTIVE_IDENTICAL_VERTICES_2D = CONSECUTIVE_IDENTICAL_VERTICES_2D
    DUP_COORDS_CHECK_Z = No
    MISSING_TEXTURE_COORDINATES = MISSING_TEXTURE_COORDINATES
    MISSING_VERTEX_NORMALS = MISSING_VERTEX_NORMALS
    NAN_REMOVAL = NAN_REMOVAL
    NULL_REMOVAL = NULL_REMOVAL
    OGC_SIMPLE_CHECK = OGC_SIMPLE_CHECK
    OGC_VALID_CHECK = OGC_VALID_CHECK
    PLANAR_SURFACE = PLANAR_SURFACE
    PLANAR_TOLERANCE_MODE = Auto
    PRESETS = All
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%MISSING_VERTEX_NORMALS%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"
    SELF_INTERSECTING = SELF_INTERSECTING
    SHELL_VALIDATION = SHELL_VALIDATION
    SOLID_VOID_REPAIR = SOLID_VOID_REPAIR
    TYPE_REPAIR = TYPE_REPAIR
    PASSED -> Intersector_2
    FAILED -> Intersector_2
    REPAIRED -> Intersector_2
Note: Intersect lines and extensions
Intersector_2
    DUPLICATE_Z_NODES = No
    OV_ATTR = _overlaps
    PERFORM_SELF_INTERSECTION = No
    SEG_ATTR = _segments
    SEPARATE_COLLINEAR_SEGMENTS = No
    INTERSECTED -> TopologyBuilder_2 [LINE]
Note: Recreate query topology
TopologyBuilder_2
    ALLOW_CYCLES = No
    ALL_EDGES = Yes
    CLEAN_DATA = Yes
    MAX = 0
    OVERLAPPING_MODE = No
    PROP_ATTRS = No
    LINE -> Tester
Note: Remove extended dangles
Tester
    BOOL_OP = COMPOSITE
    COMPOSITE_TEST = "(1 OR 2) AND 3"
    TEST_CLAUSE:
      TEST @Evaluate(abs(@Value(_left_edge))) = @Value(_arc_id)
      TEST @Evaluate(abs(@Value(_right_edge))) = @Value(_arc_id)
      TEST @Value(_smartcleaner_extended) = 1
    TEST_MODE = Automatic
    FAILED -> AttributeRemover
Note: Clean up attributes
AttributeRemover
    REMOVE_ATTRS = _overlaps,_segments,_arc_id,_right_polygon,_left_polygon,_right_edge,_left_edge,_from_node,_to_node,_polygons
    -> TopologyBuilder_3 [LINE]
Note: Recreate query topology / with extensions removed
TopologyBuilder_3
    ALLOW_CYCLES = No
    ALL_EDGES = Yes
    CLEAN_DATA = Yes
    MAX = 0
    OVERLAPPING_MODE = No
    PROP_ATTRS = No
    LINE -> LengthCalculator
Note: Calculate line length
LengthCalculator
    DIM = 2
    LEN_ATTR = _length
    MULT = 1
    -> Tester_2
Note: Remove any dangling / lines less than Overshoot / Length
Tester_2
    BOOL_OP = COMPOSITE
    COMPOSITE_TEST = "(1 OR 2) AND 3"
    TEST_CLAUSE:
      TEST @Evaluate(abs(@Value(_left_edge))) = @Value(_arc_id)
      TEST @Evaluate(abs(@Value(_right_edge))) = @Value(_arc_id)
      TEST @Value(_length) < $(VAL)
    TEST_MODE = Automatic
    FAILED -> AttributeRemover_2
Note: Clean up attributes
AttributeRemover_2
    REMOVE_ATTRS = _smartcleaner_extended,_arc_id,_right_polygon,_left_polygon,_right_edge,_left_edge,_from_node,_to_node,_polygons,_length
    -> CLEANED (output)
CLEANED (output)
<REJECTED> (output)
