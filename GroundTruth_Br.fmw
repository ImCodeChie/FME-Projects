FME workspace GroundTruth_Br.fmw

Parameters:
- SourceDataset_SHAPEFILE = $(FME_MF_DIR)Input_Data_2\Conab\CANA-GO_Safra_2010_2011\GO_CANA_1011.shp   # Source Esri Shapefile(s)
- SourceDataset_SHAPEFILE_17 = $(FME_MF_DIR)Input_Data_2\Conab\CANA-GO_Safra_2011_2012\GO_CANA_1112.shp   # Source Esri Shapefile(s)
- SourceDataset_SHAPEFILE_33 = $(FME_MF_DIR)Input_Data_2\Conab\CANA-MS_Safra_2012_2013\MS_CANA_1213.shp   # Source Esri Shapefile(s)
- SourceDataset_SHAPEFILE_11 = $(FME_MF_DIR)Input_Data_2\Conab\CANA-MT_Safra_2012_2013\MT_CANA_1213.shp   # Source Esri Shapefile(s)
- SourceDataset_SHAPEFILE_15 = $(FME_MF_DIR)Input_Data_2\Conab\CANA-SP_Safra_2012_2013\SP_CANA_1213.shp   # Source Esri Shapefile(s)
- SourceDataset_SHAPEFILE_24 = $(FME_MF_DIR)Input_Data_2\WorldCereal\2016_BR_JECAM_CIRAD_POLY_111\2016_BR_JECAM_CIRAD_POLY_111.shp   # Source Esri Shapefile(s)
- SourceDataset_SHAPEFILE_29 = $(FME_MF_DIR)Input_Data_2\WorldCereal\2017_BR_JECAM_CIRAD_POLY_111\2017_BR_JECAM_CIRAD_POLY_111.shp   # Source Esri Shapefile(s)
- SourceDataset_SHAPEFILE_26 = $(FME_MF_DIR)Input_Data_2\WorldCereal\2020_BR_LEM-MAR_POLY_110\2020_BR_LEM-MAR_POLY_110.shp   # Source Esri Shapefile(s)
- SourceDataset_OGCGEOPACKAGE_17 = $(FME_MF_DIR)Results\Final\Minas Geraes\SUGARCANE_Minas Geraes.gpkg   # GeoPackage File
- SourceDataset_OGCGEOPACKAGE_13 = $(FME_MF_DIR)Results\Final\Paraná\SUGARCANE_Paraná.gpkg   # GeoPackage File
- SourceDataset_OGCGEOPACKAGE_21 = $(FME_MF_DIR)Results\Final\Pernambouc\SUGARCANE_Pernambouc.gpkg   # GeoPackage File
- SourceDataset_OGCGEOPACKAGE_15 = $(FME_MF_DIR)Results\Final\São Paulo\SUGARCANE_Sao Paulo.gpkg   # GeoPackage File
- SourceDataset_OGCGEOPACKAGE_19 = $(FME_MF_DIR)Input_Data_2\Geosys_Data\SUGARCANE\SUGARCANE\2017\groundtruth_worldcereal_SUGARCANE_2017.gpkg   # GeoPackage File
- SourceDataset_OGCGEOPACKAGE = $(FME_MF_DIR)Results\Final\Goiás\SUGARCANE_Goiás.gpkg   # GeoPackage File
- SourceDataset_SHAPEFILE_16 = ""$(FME_MF_DIR)Input_Data_2\Geosys_Digitized\OneDrive_1_03-11-2023\safra\BRAZIL_2018_2019_crop1_v5.2.shp" "$(FME_MF_DIR)Input_Data_2\Geosys_Digitized\OneDrive_1_03-11-2023\safra\BRAZIL_2019_2020_crop1_v5.2.shp" "$(FME_MF_DIR)Input_Data_2\Geosys_Digitized\OneDrive_1_03-11-2023\safra\BRAZIL_2020_2021_crop1_v5.2.shp" "$(FME_MF_DIR)Input_Data_2\Geosys_Digitized\OneDrive_1_03-11-2023\safra\BRAZIL_2021_2022_crop1_v5.2.shp""   # Source Esri Shapefile(s)
- SourceDataset_SHAPEFILE_18 = ""$(FME_MF_DIR)Input_Data_2\Geosys_Digitized\OneDrive_1_03-11-2023\safrinha\BRAZIL_2018_2018_crop2_v5.2.shp" "$(FME_MF_DIR)Input_Data_2\Geosys_Digitized\OneDrive_1_03-11-2023\safrinha\BRAZIL_2019_2019_crop2_v5.2.shp" "$(FME_MF_DIR)Input_Data_2\Geosys_Digitized\OneDrive_1_03-11-2023\safrinha\BRAZIL_2020_2020_crop2_v5.2.shp" "$(FME_MF_DIR)Input_Data_2\Geosys_Digitized\OneDrive_1_03-11-2023\safrinha\BRAZIL_2021_2021_crop2_v5.2.shp" "$(FME_MF_DIR)Input_Data_2\Geosys_Digitized\OneDrive_1_03-11-2023\safrinha\BRAZIL_2022_2022_crop2_v5.2.shp""   # Source Esri Shapefile(s)
- DestDataset_OGCGEOPACKAGE_2 = $(FME_MF_DIR)Input_Data_2\Results_2\Conab_SISSER\Conab_SISSER_2.gpkg   # GeoPackage File
- DestDataset_SHAPEFILE = $(FME_MF_DIR)Input_Data_2\Results_2\Final_Output\Per_Year   # Destination Esri Shapefile Folder
- SourceDataset_SHAPEFILE_27 = ""$(FME_MF_DIR)Input_Data_2\Geosys_Data\SUGARCANE\SUGARCANE\2016_2021\2016_2016_SISSER.shp" "$(FME_MF_DIR)Input_Data_2\Geosys_Data\SUGARCANE\SUGARCANE\2016_2021\2022_SISSER.shp""   # Source Esri Shapefile(s)
- SourceDataset_SHAPEFILE_31 = $(FME_MF_DIR)Input_Data_2\gadm36_BRA_shp\gadm36_BRA_2.shp   # Source Esri Shapefile(s)
- DestDataset_SHAPEFILE_2 = $(FME_MF_DIR)Input_Data_2\Results_2\Final_Output\Per_Year   # Destination Esri Shapefile Folder
- DestDataset_SHAPEFILE_3 = $(FME_MF_DIR)Input_Data_2\Results_2\Final_Output\Per_Year   # Destination Esri Shapefile Folder
- DestDataset_SHAPEFILE_4 = $(FME_MF_DIR)Input_Data_2\Results_2\Final_Output\Per_Year   # Destination Esri Shapefile Folder
- DestDataset_SHAPEFILE_5 = $(FME_MF_DIR)Input_Data_2\Results_2\Final_Output\Per_Year   # Destination Esri Shapefile Folder
- DestDataset_SHAPEFILE_6 = $(FME_MF_DIR)Input_Data_2\Results_2\Final_Output\Per_Year   # Destination Esri Shapefile Folder
- SourceDataset_SHAPEFILE_14 = $(FME_MF_DIR)Input_Data_2\OSM\Brazil\centro-oeste-latest-free.shp\gis_osm_landuse_a_free_1.shp   # Source Esri Shapefile(s)
- SourceDataset_SHAPEFILE_35 = $(FME_MF_DIR)Input_Data_2\OSM\Brazil\nordeste-latest-free.shp\gis_osm_landuse_a_free_1.shp   # Source Esri Shapefile(s)
- SourceDataset_SHAPEFILE_28 = $(FME_MF_DIR)Input_Data_2\OSM\Brazil\norte-latest-free.shp\gis_osm_landuse_a_free_1.shp   # Source Esri Shapefile(s)
- SourceDataset_SHAPEFILE_30 = $(FME_MF_DIR)Input_Data_2\OSM\Brazil\sudeste-latest-free.shp\gis_osm_landuse_a_free_1.shp   # Source Esri Shapefile(s)
- SourceDataset_SHAPEFILE_32 = $(FME_MF_DIR)Input_Data_2\OSM\Brazil\sul-latest-free.shp\gis_osm_landuse_a_free_1.shp   # Source Esri Shapefile(s)
- SourceDataset_OGCGEOPACKAGE_8 = $(FME_MF_DIR)Input_Data_2\OSM\QuickOSM\landuse.gpkg   # GeoPackage File
- DestDataset_SHAPEFILE_7 = $(FME_MF_DIR)Input_Data_2\Results_2\Final_Output\Per_Year   # Destination Esri Shapefile Folder
- SourceDataset_SHAPEFILE_34 = $(FME_MF_DIR)Input_Data_2\Geosys_Data\SUGARCANE\SUGARCANE\USINAS_CANA_BR_ATIVAS_2021.shp   # Source Esri Shapefile(s)
- DestDataset_SHAPEFILE_8 = $(FME_MF_DIR)Input_Data_2\Results_2\Conab_SISSER   # Destination Esri Shapefile Folder
- DestDataset_SHAPEFILE_9 = $(FME_MF_DIR)Input_Data_2\Results_2\Conab_SISSER   # Destination Esri Shapefile Folder
- DestDataset_SHAPEFILE_10 = $(FME_MF_DIR)Input_Data_2\Results_2\Final_Output\Per_Year   # Destination Esri Shapefile Folder
- DestDataset_SHAPEFILE_12 = $(FME_MF_DIR)Input_Data_2\Results_2\Final_Output\Per_Year   # Destination Esri Shapefile Folder
- DestDataset_SHAPEFILE_13 = $(FME_MF_DIR)Input_Data_2\Results_2\Final_Output\For_QC   # Destination Esri Shapefile Folder
- DestDataset_SHAPEFILE_19 = $(FME_MF_DIR)Input_Data_2\Results_2\All.xlsx   # Destination Esri Shapefile Folder
- DestDataset_SHAPEFILE_20 = $(FME_MF_DIR)Input_Data_2\Results_2\Final_Output\All_refined   # Destination Esri Shapefile Folder

Readers:
- SHAPEFILE_1: SHAPEFILE from $(SourceDataset_SHAPEFILE)
- SHAPEFILE_2: SHAPEFILE from $(SourceDataset_SHAPEFILE_17)
- SHAPEFILE_3: SHAPEFILE from $(SourceDataset_SHAPEFILE_33)
- SHAPEFILE_4: SHAPEFILE from $(SourceDataset_SHAPEFILE_11)
- SHAPEFILE_5: SHAPEFILE from $(SourceDataset_SHAPEFILE_15)
- SHAPEFILE_6: SHAPEFILE from $(SourceDataset_SHAPEFILE_24)
- SHAPEFILE_7: SHAPEFILE from $(SourceDataset_SHAPEFILE_29)
- SHAPEFILE_8: SHAPEFILE from $(SourceDataset_SHAPEFILE_26)
- OGCGEOPACKAGE_1: OGCGEOPACKAGE from $(SourceDataset_OGCGEOPACKAGE)
- OGCGEOPACKAGE_2: OGCGEOPACKAGE from $(SourceDataset_OGCGEOPACKAGE_17)
- OGCGEOPACKAGE_3: OGCGEOPACKAGE from $(SourceDataset_OGCGEOPACKAGE_13)
- OGCGEOPACKAGE_4: OGCGEOPACKAGE from $(SourceDataset_OGCGEOPACKAGE_21)
- OGCGEOPACKAGE_5: OGCGEOPACKAGE from $(SourceDataset_OGCGEOPACKAGE_15)
- OGCGEOPACKAGE_6: OGCGEOPACKAGE from $(SourceDataset_OGCGEOPACKAGE_19)
- SHAPEFILE_9: SHAPEFILE from $(SourceDataset_SHAPEFILE_16)
- SHAPEFILE_10: SHAPEFILE from $(SourceDataset_SHAPEFILE_18)
- SHAPEFILE_12: SHAPEFILE from $(SourceDataset_SHAPEFILE_27)
- SHAPEFILE_13: SHAPEFILE from $(SourceDataset_SHAPEFILE_31)
- SHAPEFILE_19: SHAPEFILE from $(SourceDataset_SHAPEFILE_14)
- SHAPEFILE_20: SHAPEFILE from $(SourceDataset_SHAPEFILE_35)
- SHAPEFILE_21: SHAPEFILE from $(SourceDataset_SHAPEFILE_28)
- SHAPEFILE_22: SHAPEFILE from $(SourceDataset_SHAPEFILE_30)
- SHAPEFILE_23: SHAPEFILE from $(SourceDataset_SHAPEFILE_32)
- OGCGEOPACKAGE_7: OGCGEOPACKAGE from $(SourceDataset_OGCGEOPACKAGE_8)
- SHAPEFILE_25: SHAPEFILE from $(SourceDataset_SHAPEFILE_34)

Writers:
- OGCGEOPACKAGE_13: OGCGEOPACKAGE to $(DestDataset_OGCGEOPACKAGE_2)
- SHAPEFILE_11: SHAPEFILE to $(DestDataset_SHAPEFILE)
- SHAPEFILE_14: SHAPEFILE to $(DestDataset_SHAPEFILE_2)
- SHAPEFILE_15: SHAPEFILE to $(DestDataset_SHAPEFILE_3)
- SHAPEFILE_16: SHAPEFILE to $(DestDataset_SHAPEFILE_4)
- SHAPEFILE_17: SHAPEFILE to $(DestDataset_SHAPEFILE_5)
- SHAPEFILE_18: SHAPEFILE to $(DestDataset_SHAPEFILE_6)
- SHAPEFILE_24: SHAPEFILE to $(DestDataset_SHAPEFILE_7)
- SHAPEFILE_26: SHAPEFILE to $(DestDataset_SHAPEFILE_8)
- SHAPEFILE_27: SHAPEFILE to $(DestDataset_SHAPEFILE_9)
- SHAPEFILE_28: SHAPEFILE to $(DestDataset_SHAPEFILE_10)
- SHAPEFILE_29: SHAPEFILE to $(DestDataset_SHAPEFILE_12)
- SHAPEFILE_30: SHAPEFILE to $(DestDataset_SHAPEFILE_13)
- SHAPEFILE_31: SHAPEFILE to $(DestDataset_SHAPEFILE_19)
- SHAPEFILE_32: SHAPEFILE to $(DestDataset_SHAPEFILE_20)

Bookmark: SUGARCANE_Brazil
2016_BR_JECAM_CIRAD_POLY_111 (reader SHAPEFILE_6) [off]
    attributes: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
2017_BR_JECAM_CIRAD_POLY_111 (reader SHAPEFILE_7) [off]
    attributes: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
2020_BR_LEM-MAR_POLY_110 (reader SHAPEFILE_8) [off]
    attributes: id varchar(80), Mar_2020 varchar(80), CT varchar(4), LC varchar(4), IRR varchar(4), valtime date, sampleID varchar(100)
groundtruth_worldcereal_SUGARCANE_2017 (reader OGCGEOPACKAGE_6)
    attributes: Id mediumint, Country text(30), SiteName text(30), DataSource int, AcquiDate date, LandCover text(50), CropType1 text(50), CropType2 text(50), CropType3 text(50), SOS date, EOS date, Irrigated int, Intercrop int, Weeding int, Area_ha double, KeyWords text(150), Landcove_1 text(80), valtime date, CT text(4), LC text(4), IRR text(4), sampleID text(100), fid int,PrimaryKey
    -> groundtruth_worldcereal_SUGARCANE_2017
    -> Reprojector_7
Reprojector_7
    DEST = EPSG:3857
    INTERPOLATION_TYPE_NAME = Nearest Neighbor
    RASTER_CELL_SIZE = Preserve Cells
    RASTER_TOLERANCE = 0.0
    REPROJECTED -> AttributeManager_6
AttributeManager_6
    ATTR_TABLE:
      RENAME_SET_VALUE Id > Id_WorldCereal
      SET_TO Source = WorldCereal
      SET_TO Sow_W = @Left(@Value(AcquiDate),4)
      SET_TO Harvest_W = @Evaluate(@Value(Sow_W)+1)
    USER_EXPOSED_ATTRIBUTES = Source
    -> AreaOnAreaOverlayer_2 [AREA]
groundtruth_worldcereal_SUGARCANE_2017: Inspector
SUGARCANE_Goiás_V3 (reader OGCGEOPACKAGE_1)
    attributes: usr_idcustomer mediumint, frm_name text, sfd_id mediumint, legacy_id text, unique_id text, fld_name text, sfd_geometry text, fld_acreage double, ssf_season text, sfd_sowingdate date, crp_code text, ssf_plantedarea text, ssf_plantedpercentage text, esti_emergence text, esti_sowing text, cst_code text, date_part double, sfd_id_2 mediumint, fid int,PrimaryKey
    -> Reprojector_4
SUGARCANE_Minas Geraes_V3 (reader OGCGEOPACKAGE_2)
    attributes: usr_idcustomer mediumint, frm_name text, sfd_id mediumint, legacy_id text, unique_id text, fld_name text, sfd_geometry text, fld_acreage double, ssf_season text, sfd_sowingdate date, crp_code text, ssf_plantedarea text, ssf_plantedpercentage text, esti_emergence text, esti_sowing text, cst_code text, date_part double, sfd_id_2 mediumint, fid int,PrimaryKey
    -> Reprojector_4
SUGARCANE_Paraná_V3 (reader OGCGEOPACKAGE_3)
    attributes: usr_idcustomer mediumint, frm_name text, sfd_id mediumint, legacy_id text, unique_id text, fld_name text, sfd_geometry text, fld_acreage double, ssf_season text, sfd_sowingdate date, crp_code text, ssf_plantedarea text, ssf_plantedpercentage text, esti_emergence text, esti_sowing text, cst_code text, date_part double, sfd_id_2 mediumint, fid int,PrimaryKey
    -> Reprojector_4
SUGARCANE_Pernambouc_V3 (reader OGCGEOPACKAGE_4)
    attributes: usr_idcustomer mediumint, frm_name text, sfd_id mediumint, legacy_id text, unique_id text, fld_name text, sfd_geometry text, fld_acreage double, ssf_season text, sfd_sowingdate date, crp_code text, ssf_plantedarea text, ssf_plantedpercentage text, esti_emergence text, esti_sowing text, cst_code text, date_part double, sfd_id_2 mediumint, fid int,PrimaryKey
    -> Reprojector_4
SUGARCANE_Sao Paulo_V3 (reader OGCGEOPACKAGE_5)
    attributes: usr_idcustomer mediumint, frm_name text, sfd_id mediumint, legacy_id text, unique_id text, fld_name text, sfd_geometry text, fld_acreage double, ssf_season text, sfd_sowingdate date, crp_code text, ssf_plantedarea text, ssf_plantedpercentage text, esti_emergence text, esti_sowing text, cst_code text, date_part double, sfd_id_2 mediumint, fid int,PrimaryKey
    -> Reprojector_4
Reprojector_4
    DEST = EPSG:3857
    INTERPOLATION_TYPE_NAME = Nearest Neighbor
    RASTER_CELL_SIZE = Preserve Cells
    RASTER_TOLERANCE = 0.0
    REPROJECTED -> AttributeManager_7
AttributeManager_7
    ATTR_TABLE:
      SET_TO Source = @Value(cst_code)
      SET_TO sfd_swg = @Left(@Value(sfd_sowingdate),4)
      SET_TO sfd_swg_2 = @Evaluate(@Value(sfd_swg)+1)
    USER_EXPOSED_ATTRIBUTES = Source
    -> AreaOnAreaOverlayer_2 [AREA]
AreaOnAreaOverlayer_2
    ACCUM_ATTRS_NAME = Merge Incoming Attributes
    CLEANING_TOLERANCE = Automatic
    CONNECT_Z_MODE = First Wins
    DEAGGREGATE_INPUT = Yes
    GROUP_BY = sfd_id Id_WorldCereal
    OVC_ATTR = _overlaps
    AREA -> Aggregator
Aggregator
    ACCUM_ATTRS_NAME = Merge Incoming Attributes
    AGGREGATE_TYPE = Homogeneous Collection (If Possible)
    GROUP_BY = sfd_id Id_WorldCereal
    MODE = Geometry - Assemble One Level
    SEP = ,
    AGGREGATE -> AreaOnAreaOverlayer_4 [AREA]
BRAZIL_2018_2019_crop1_v5.2 (reader SHAPEFILE_9)
    attributes: ID number(11,0), crp_code varchar(254), crp_id number(11,0), crp_type varchar(254), crp_typeid number(11,0), sfd_sowing varchar(254), sowing varchar(254), harvest varchar(254), season varchar(254), state varchar(254), source varchar(254), area number(31,15), QC number(11,0), ml_split number(11,0)
    -> Reprojector_2
BRAZIL_2019_2020_crop1_v5.2 (reader SHAPEFILE_9)
    attributes: ID number(11,0), crp_code varchar(254), crp_id number(11,0), crp_type varchar(254), crp_typeid number(11,0), sfd_sowing varchar(254), sowing varchar(254), harvest varchar(254), season varchar(254), state varchar(254), source varchar(254), area number(31,15), QC number(11,0), ml_split number(11,0)
    -> Reprojector_2
BRAZIL_2020_2021_crop1_v5.2 (reader SHAPEFILE_9)
    attributes: ID number(20,0), crp_code varchar(254), crp_id number(20,0), crp_type varchar(254), crp_typeid number(20,0), sfd_sowing varchar(254), sowing varchar(254), harvest varchar(254), season varchar(254), state varchar(254), source varchar(254), area number(31,15), QC number(20,0), ml_split number(20,0)
    -> Reprojector_2
BRAZIL_2021_2022_crop1_v5.2 (reader SHAPEFILE_9)
    attributes: ID number(20,0), crp_code varchar(254), crp_id number(20,0), crp_type varchar(254), crp_typeid number(20,0), sfd_sowing varchar(254), sowing varchar(254), harvest varchar(254), season varchar(254), state varchar(254), source varchar(254), area number(31,15), QC number(20,0), ml_split number(20,0)
    -> Reprojector_2
Reprojector_2
    DEST = EPSG:3857
    INTERPOLATION_TYPE_NAME = Nearest Neighbor
    RASTER_CELL_SIZE = Preserve Cells
    RASTER_TOLERANCE = 0.0
    REPROJECTED -> TestFilter
TestFilter
    DEFAULT_VALUE = <UNFILTERED>
    PASSED_TEST_GROUP_OUTPUT = FIRST
    TEST_LIST = "BOOL_OP,OR,COMPOSITE_TEST,""""""1"""""",TEST_CLAUSE,TEST @Value(crp_type) = SUGARCANE",Sugarcane
    Sugarcane -> AttributeManager_2
AttributeManager_2
    ATTR_TABLE:
      RENAME_SET_VALUE ID > ID_Safra
      SET_TO Source = @Value(source)
    USER_EXPOSED_ATTRIBUTES = Source
    -> ChangeDetector [ORIGINAL]
BRAZIL_2018_2018_crop2_v5.2 (reader SHAPEFILE_10)
    attributes: ID number(20,0), crp_code varchar(254), crp_id number(20,0), crp_type varchar(254), crp_typeid number(20,0), sfd_sowing varchar(254), sowing varchar(254), harvest varchar(254), season varchar(254), state varchar(254), source varchar(254), area number(31,15), QC number(20,0), ml_split number(20,0)
    -> Reprojector_6
BRAZIL_2019_2019_crop2_v5.2 (reader SHAPEFILE_10)
    attributes: ID number(11,0), crp_code varchar(254), crp_id number(11,0), crp_type varchar(254), crp_typeid number(11,0), sfd_sowing varchar(254), sowing varchar(254), harvest varchar(254), season varchar(254), state varchar(254), source varchar(254), area number(31,15), QC number(11,0), ml_split number(11,0)
    -> Reprojector_6
BRAZIL_2020_2020_crop2_v5.2 (reader SHAPEFILE_10)
    attributes: ID number(11,0), crp_code varchar(254), crp_id number(11,0), crp_type varchar(254), crp_typeid number(11,0), sfd_sowing varchar(254), sowing varchar(254), harvest varchar(254), season varchar(254), state varchar(254), source varchar(254), area number(31,15), QC number(11,0), ml_split number(11,0)
    -> Reprojector_6
BRAZIL_2021_2021_crop2_v5.2 (reader SHAPEFILE_10)
    attributes: ID number(20,0), crp_code varchar(254), crp_id number(20,0), crp_type varchar(254), crp_typeid number(20,0), sfd_sowing varchar(254), sowing varchar(254), harvest varchar(254), season varchar(254), state varchar(254), source varchar(254), area number(31,15), QC number(20,0), ml_split number(20,0)
    -> Reprojector_6
BRAZIL_2022_2022_crop2_v5.2 (reader SHAPEFILE_10)
    attributes: ID number(20,0), crp_code varchar(254), crp_id number(20,0), crp_type varchar(254), crp_typeid number(20,0), sfd_sowing varchar(254), sowing varchar(254), harvest varchar(254), season varchar(254), state varchar(254), source varchar(254), area number(31,15), QC number(20,0), ml_split number(20,0)
    -> Reprojector_6
Reprojector_6
    DEST = EPSG:3857
    INTERPOLATION_TYPE_NAME = Nearest Neighbor
    RASTER_CELL_SIZE = Preserve Cells
    RASTER_TOLERANCE = 0.0
    REPROJECTED -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(crp_type) = SUGARCANE",Sugarcane
    Sugarcane -> AttributeManager_3
AttributeManager_3
    ATTR_TABLE:
      RENAME_SET_VALUE ID > ID_Safrina
      SET_TO Source = @Value(source)
    USER_EXPOSED_ATTRIBUTES = Source
    -> ChangeDetector [REVISED]
ChangeDetector
    BLANK_AND_MISSING_NAMES_TRAITS_DIFFER = Yes
    CHECK_COORDINATE_SYSTEMS = No
    LENIENT_MATCH = No
    MATCH = FULL
    UNCHANGED_OUTPUT = Output Original
    UPSERT_MODE = No
    INSERTED -> FeatureJoiner [LEFT]
    UNCHANGED -> FeatureJoiner [RIGHT]
FeatureJoiner
    ATTR_CONFLICT_RES = Prefer Left
    GEOMETRY_HANDLING = Prefer Left
    JOIN_KEYS = ID_Safrina ID_Safra AUTO
    JOIN_MODE = Full
    JOINED -> AreaOnAreaOverlayer_4 [AREA]
AreaOnAreaOverlayer_4
    ACCUM_ATTRS_NAME = Merge Incoming Attributes
    CLEANING_TOLERANCE = Automatic
    CONNECT_Z_MODE = First Wins
    DEAGGREGATE_INPUT = Yes
    GROUP_BY = sfd_id ID_Safra ID_Safrina Id_WorldCereal
    OVC_ATTR = _overlaps
    AREA -> Aggregator_2
Aggregator_2
    ACCUM_ATTRS_NAME = Merge Incoming Attributes
    AGGREGATE_TYPE = Homogeneous Collection (If Possible)
    GROUP_BY = sfd_id ID_Safra ID_Safrina Id_WorldCereal
    MODE = Geometry - Assemble One Level
    SEP = ,
    AGGREGATE -> AreaOnAreaOverlayer [AREA]
gadm36_BRA_2 (reader SHAPEFILE_13)
    attributes: GID_0 varchar(80), NAME_0 varchar(80), GID_1 varchar(80), NAME_1 varchar(80), NL_NAME_1 varchar(80), GID_2 varchar(80), NAME_2 varchar(80), VARNAME_2 varchar(80), NL_NAME_2 varchar(80), TYPE_2 varchar(80), ENGTYPE_2 varchar(80), CC_2 varchar(80), HASC_2 varchar(80)
    -> Reprojector_9
Reprojector_9
    DEST = EPSG:3857
    INTERPOLATION_TYPE_NAME = Nearest Neighbor
    RASTER_CELL_SIZE = Preserve Cells
    RASTER_TOLERANCE = 0.0
    REPROJECTED -> AttributeManager_23
AttributeManager_23
    ATTR_TABLE:
      REMOVE GID_0
      REMOVE NAME_0
      REMOVE GID_1
      REMOVE NL_NAME_1
      REMOVE GID_2
      REMOVE VARNAME_2
      REMOVE NL_NAME_2
      REMOVE TYPE_2
      REMOVE ENGTYPE_2
      REMOVE CC_2
      REMOVE HASC_2
    -> Junction_2
Junction_2
    -> AttributeManager_5
    -> Clipper [CLIPPER]
    -> Clipper_2 [CLIPPER]
AttributeManager_5
    -> SpatialRelator [Supplier]
landuse_farm_landuse_farmland (reader OGCGEOPACKAGE_7)
    attributes: full_id text, osm_id text, osm_type text, landuse text, agricultural text, mobile text, contact:youtube text, contact:linkedin text, tidal text, genus:wikidata text, maintained text, abandoned:operator text, magic_wand text, proposed text, species:wikidata text, vending text, network:operator text, network text, abandoned text, fruit text, reservation text, bbq text, FITOFISION text, source_ref text, lanes text, survey:date text, managed text, ref:senasag:sa text, lbcs:activity:name text, contact:mobile text,
      plant text, date:decade text, denotation text, animal_keeping:type text, image text, meadow text, reservoir_type text, source:alt_name text, addr:district text, private text, CHAVE text, livestock text, material text, plant:source text, ciultivo text, culture text, aerialway:bubble text, cuisine text, lit text, horse text, industrial text, resource text, addr:county text, year_of_construction text, government text, ref:whc text, historic:civilization text, salt text, woodland text, service text,
      branch text, addr:neighbourhood text, prison_camp text, abandoned:amenity text, craft text, shape_leng text, shape_area text, objectid text, area_ha text, population text, description:en text, addr:housename text, seasonal text, product text, wall text, ref:cadastre text, source_1 text, official_name text, roof:shape text, roof:orientation text, roof:material text, roof:height text, building:material text, contact:whatsapp text, contact:instagram text, source:landuse text, source:geometry:date text, operator:wikidata text, internet_access:ssid text, internet_access:fee text,
      internet_access text, source:image text, wheelchair text, brand text, IPP:CodTrecho text, IPP:CodQuadra text, IPP:CodNP text, IPP:CodLote text, description_2 text, denomination text, vehicle text, tourist_bus text, motorcycle text, motorcar text, motor_vehicle text, hov text, goods text, emergency text, bicycle text, 4wd_only text, aeroway text, office text, tracktype text, farmyard text, building:levels text, owner:type text, addr:typearea text, addr:areatype text, religion text, designation text,
      reg_name text, stars text, outdoor_seating text, residential text, height text, fence_type text, sector text, contact:phone text, ruins text, activity text, email text, is_in:village text, name:zu text, name:uk text, name:pl text, name:no text, name:nl text, name:lb text, name:ka text, name:ig text, name:fr text, name:el text, name:de text, name:ca text, landcover text, highway text, source:date text, disused text, heritage:operator text, heritage text,
      species text, leaf_cycle text, genus text, addr:state text, leaf_type text, note:pt text, source:url text, proposed:name text, proposed:landuse text, noexit text, source:name text, is_in:region text, ladn text, addr:place text, disused:landuse text, is_in:hamlet text, water text, shop text, man_made text, flood_prone text, organic text, source:geometry text, sport text, name:pt text, addr:country text, layer text, wetland text, building text, leisure text, fishing text,
      surface text, smoothness text, psv text, parking text, maxstay text, hgv text, foot text, fee text, capacity text, bdouble text, name:zh-Hant text, name:la text, name:ko text, name:ja text, name:it text, name:es text, intermittent text, hazard_type text, hazard_prone text, id text, CODE_12 text, CLC:year text, CLC:id text, animal_keeping text, Shape_Area_2 text, opening_hours text, nohousenumber text, source:description text, old_name text, historic text,
      irrigation text, animal text, barrier text, farmland text, Id_2 text, start_date text, old_name:1940 text, addr:postcode text, access text, addr:hamlet text, wikimedia_commons text, ref text, animal_breeding text, natural text, trees text, name:en text, ownership text, owner text, operator:type text, operator:short text, tourism text, place text, short_name text, amenity text, contact:website text, contact:facebook text, contact:email text, produce text, crop_1 text, website text,
      phone text, loc_name text, addr:suburb text, addr:street text, addr:housenumber text, addr:city text, alt_name text, ele text, is_in:city text, description text, operator text, wikipedia text, wikidata text, source:sccn text, sccn text, postal_code text, is_in:state_code text, is_in:state text, is_in:country_code text, is_in:country text, boundary text, admin_level text, name text, crop text, type text, fid int,PrimaryKey
    -> AttributeManager_24
AttributeManager_24
    ATTR_TABLE:
      RENAME_SET_VALUE osm_id > osm_id_2
      REMOVE mobile
      REMOVE contact:youtube
      REMOVE contact:linkedin
      REMOVE tidal
      REMOVE genus:wikidata
      REMOVE maintained
      REMOVE abandoned:operator
      REMOVE magic_wand
      REMOVE proposed
      REMOVE species:wikidata
      REMOVE vending
      REMOVE network:operator
      REMOVE network
      REMOVE abandoned
      REMOVE fruit
      REMOVE reservation
      REMOVE bbq
      REMOVE FITOFISION
      REMOVE source_ref
      REMOVE lanes
      REMOVE survey:date
      REMOVE managed
      REMOVE ref:senasag:sa
      REMOVE lbcs:activity:name
      REMOVE contact:mobile
      REMOVE plant
      REMOVE date:decade
      REMOVE denotation
      REMOVE animal_keeping:type
      REMOVE image
      REMOVE meadow
      REMOVE reservoir_type
      REMOVE source:alt_name
      REMOVE addr:district
      REMOVE private
      REMOVE CHAVE
      REMOVE livestock
      REMOVE material
      REMOVE plant:source
      REMOVE ciultivo
      REMOVE culture
      REMOVE aerialway:bubble
      REMOVE cuisine
      REMOVE lit
      REMOVE horse
      REMOVE industrial
      REMOVE resource
      REMOVE addr:county
      REMOVE year_of_construction
      REMOVE government
      REMOVE ref:whc
      REMOVE historic:civilization
      REMOVE salt
      REMOVE woodland
      REMOVE service
      REMOVE branch
      REMOVE addr:neighbourhood
      REMOVE prison_camp
      REMOVE abandoned:amenity
      REMOVE craft
      REMOVE shape_leng
      REMOVE shape_area
      REMOVE objectid
      REMOVE area_ha
      REMOVE population
      REMOVE description:en
      REMOVE addr:housename
      REMOVE seasonal
      REMOVE product
      REMOVE wall
      REMOVE ref:cadastre
      REMOVE source_1
      REMOVE official_name
      REMOVE roof:shape
      REMOVE roof:orientation
      REMOVE roof:material
      REMOVE roof:height
      REMOVE building:material
      REMOVE contact:whatsapp
      REMOVE contact:instagram
      REMOVE source:landuse
      REMOVE source:geometry:date
      REMOVE operator:wikidata
      REMOVE internet_access:ssid
      REMOVE internet_access:fee
      REMOVE internet_access
      REMOVE source:image
      REMOVE wheelchair
      REMOVE brand
      REMOVE IPP:CodTrecho
      REMOVE IPP:CodQuadra
      REMOVE IPP:CodNP
      REMOVE IPP:CodLote
      REMOVE description_2
      REMOVE denomination
      REMOVE vehicle
      REMOVE tourist_bus
      REMOVE motorcycle
      REMOVE motorcar
      REMOVE motor_vehicle
      REMOVE hov
      REMOVE goods
      REMOVE emergency
      REMOVE bicycle
      REMOVE 4wd_only
      REMOVE aeroway
      REMOVE office
      REMOVE tracktype
      REMOVE farmyard
      REMOVE building:levels
      REMOVE owner:type
      REMOVE addr:typearea
      REMOVE addr:areatype
      REMOVE religion
      REMOVE designation
      REMOVE reg_name
      REMOVE stars
      REMOVE outdoor_seating
      REMOVE residential
      REMOVE height
      REMOVE fence_type
      REMOVE sector
      REMOVE contact:phone
      REMOVE ruins
      REMOVE activity
      REMOVE email
      REMOVE is_in:village
      REMOVE name:zu
      REMOVE name:uk
      REMOVE name:pl
      REMOVE name:no
      REMOVE name:nl
      REMOVE name:lb
      REMOVE name:ka
      REMOVE name:ig
      REMOVE name:fr
      REMOVE name:el
      REMOVE name:de
      REMOVE name:ca
      REMOVE landcover
      REMOVE highway
      REMOVE source:date
      REMOVE disused
      REMOVE heritage:operator
      REMOVE heritage
      REMOVE species
      REMOVE leaf_cycle
      REMOVE genus
      REMOVE addr:state
      REMOVE leaf_type
      REMOVE note:pt
      REMOVE source:url
      REMOVE proposed:name
      REMOVE proposed:landuse
      REMOVE noexit
      REMOVE source:name
      REMOVE is_in:region
      REMOVE ladn
      REMOVE addr:place
      REMOVE disused:landuse
      REMOVE is_in:hamlet
      REMOVE water
      REMOVE shop
      REMOVE man_made
      REMOVE flood_prone
      REMOVE organic
      REMOVE source:geometry
      REMOVE sport
      REMOVE name:pt
      REMOVE addr:country
      REMOVE layer
      REMOVE wetland
      REMOVE building
      REMOVE leisure
      REMOVE fishing
      REMOVE surface
      REMOVE smoothness
      REMOVE psv
      REMOVE parking
      REMOVE maxstay
      REMOVE hgv
      REMOVE foot
      REMOVE fee
      REMOVE capacity
      REMOVE bdouble
      REMOVE name:zh-Hant
      REMOVE name:la
      REMOVE name:ko
      REMOVE name:ja
      REMOVE name:it
      REMOVE name:es
      REMOVE intermittent
      REMOVE hazard_type
      REMOVE hazard_prone
      REMOVE id
      REMOVE CODE_12
      REMOVE CLC:year
      REMOVE CLC:id
      REMOVE animal_keeping
      REMOVE Shape_Area_2
      REMOVE opening_hours
      REMOVE nohousenumber
      REMOVE source:description
      REMOVE old_name
      REMOVE historic
      REMOVE irrigation
      REMOVE animal
      REMOVE barrier
      REMOVE farmland
      REMOVE Id_2
      REMOVE start_date
      REMOVE old_name:1940
      REMOVE addr:postcode
      REMOVE access
      REMOVE addr:hamlet
      REMOVE wikimedia_commons
      REMOVE ref
      REMOVE animal_breeding
      REMOVE natural
      REMOVE trees
      REMOVE name:en
      REMOVE ownership
      REMOVE owner
      REMOVE operator:type
      REMOVE operator:short
      REMOVE tourism
      REMOVE place
      REMOVE short_name
      REMOVE amenity
      REMOVE contact:website
      REMOVE contact:facebook
      REMOVE contact:email
      REMOVE produce
      REMOVE crop_1
      REMOVE website
      REMOVE phone
      REMOVE loc_name
      REMOVE addr:suburb
      REMOVE addr:street
      REMOVE addr:housenumber
      REMOVE addr:city
      REMOVE alt_name
      REMOVE ele
      REMOVE is_in:city
      REMOVE description
      REMOVE operator
      REMOVE wikipedia
      REMOVE wikidata
      REMOVE source:sccn
      REMOVE sccn
      REMOVE postal_code
      REMOVE is_in:state_code
      REMOVE is_in:state
      REMOVE is_in:country_code
      REMOVE is_in:country
      REMOVE boundary
      REMOVE admin_level
      REMOVE name
      SET_TO Source = OSM_2
    -> Reprojector_10
Reprojector_10
    DEST = EPSG:3857
    INTERPOLATION_TYPE_NAME = Nearest Neighbor
    RASTER_CELL_SIZE = Preserve Cells
    RASTER_TOLERANCE = 0.0
    REPROJECTED -> Junction_6
Junction_6
    -> Clipper [CANDIDATE]
    -> Clipper_2 [CANDIDATE]
Clipper_2
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> TestFilter_9
TestFilter_9
    DEFAULT_VALUE = <UNFILTERED>
    PASSED_TEST_GROUP_OUTPUT = FIRST
    TEST_LIST = "BOOL_OP,OR,COMPOSITE_TEST,""""""1"""""",TEST_CLAUSE,TEST @Value(crop) = cana-de-açúcar",cana-de-açucar,"BOOL_OP,OR,COMPOSITE_TEST,""""""1"""""",TEST_CLAUSE,TEST @Value(crop) = cana",Cana,"BOOL_OP,OR,COMPOSITE_TEST,""""""1"""""",TEST_CLAUSE,TEST @Value(crop) = sugarcane",sugarcane,"BOOL_OP,OR,COMPOSITE_TEST,""""""1"""""",TEST_CLAUSE,TEST @Value(crop) = cane",cane,"BOOL_OP,OR,COMPOSITE_TEST,""""""1"""""",TEST_CLAUSE,TEST @Value(crop) = Cane",Cane,"BOOL_OP,OR,COMPOSITE_TEST,""""""1"""""",TEST_CLAUSE,TEST @Value(crop) = sugar",sugar,"BOOL_OP,OR,COMPOSITE_TEST,""""""1"""""",TEST_CLAUSE,TEST @Value(crop) = sugarkane",sugarkane
    <UNFILTERED> -> Junction_7
Junction_7
    -> AreaOnAreaOverlayer_3 [AREA]
    -> PointOnAreaOverlayer_3 [AREA]
Clipper
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> TestFilter_7
TestFilter_7
    DEFAULT_VALUE = <UNFILTERED>
    PASSED_TEST_GROUP_OUTPUT = FIRST
    TEST_LIST = "BOOL_OP,OR,COMPOSITE_TEST,""""""1"""""",TEST_CLAUSE,TEST @Value(crop) = cana-de-açúcar",cana-de-açucar,"BOOL_OP,OR,COMPOSITE_TEST,""""""1"""""",TEST_CLAUSE,TEST @Value(crop) = cana",Cana,"BOOL_OP,OR,COMPOSITE_TEST,""""""1"""""",TEST_CLAUSE,TEST @Value(crop) = sugarcane",sugarcane,"BOOL_OP,OR,COMPOSITE_TEST,""""""1"""""",TEST_CLAUSE,TEST @Value(crop) = cane",cane,"BOOL_OP,OR,COMPOSITE_TEST,""""""1"""""",TEST_CLAUSE,TEST @Value(crop) = Cane",Cane,"BOOL_OP,OR,COMPOSITE_TEST,""""""1"""""",TEST_CLAUSE,TEST @Value(crop) = sugar",sugar,"BOOL_OP,OR,COMPOSITE_TEST,""""""1"""""",TEST_CLAUSE,TEST @Value(crop) = sugarkane",sugarkane
    cana-de-açucar -> AttributeManager_25
    Cana -> AttributeManager_25
    sugarcane -> AttributeManager_25
    cane -> AttributeManager_25
    Cane -> AttributeManager_25
    sugar -> AttributeManager_25
    sugarkane -> AttributeManager_25
AttributeManager_25
    ATTR_TABLE:
      REMOVE full_id
      REMOVE osm_type
      REMOVE landuse
      REMOVE agricultural
      REMOVE type
      REMOVE fid
      REMOVE _clipped
    -> PointOnAreaOverlayer_2 [AREA]
gis_osm_landuse_a_free_1 (reader SHAPEFILE_19)
    attributes: osm_id varchar(12), code short, fclass varchar(28), name varchar(100)
    -> Reprojector_8
gis_osm_landuse_a_free_1 (reader SHAPEFILE_20)
    attributes: osm_id varchar(12), code short, fclass varchar(28), name varchar(100)
    -> Reprojector_8
gis_osm_landuse_a_free_1 (reader SHAPEFILE_21)
    attributes: osm_id varchar(12), code short, fclass varchar(28), name varchar(100)
    -> Reprojector_8
gis_osm_landuse_a_free_1 (reader SHAPEFILE_22)
    attributes: osm_id varchar(12), code short, fclass varchar(28), name varchar(100)
    -> Reprojector_8
gis_osm_landuse_a_free_1 (reader SHAPEFILE_23)
    attributes: osm_id varchar(12), code short, fclass varchar(28), name varchar(100)
    -> Reprojector_8
Reprojector_8
    DEST = EPSG:3857
    INTERPOLATION_TYPE_NAME = Nearest Neighbor
    RASTER_CELL_SIZE = Preserve Cells
    RASTER_TOLERANCE = 0.0
    REPROJECTED -> AttributeManager_22
AttributeManager_22
    ATTR_TABLE = SET_TO Source = OSM
    -> TestFilter_6
TestFilter_6
    DEFAULT_VALUE = <UNFILTERED>
    PASSED_TEST_GROUP_OUTPUT = FIRST
    TEST_LIST = "BOOL_OP,OR,COMPOSITE_TEST,""""""1"""""",TEST_CLAUSE,TEST @Value(fclass) = farmland",farmland,"BOOL_OP,OR,COMPOSITE_TEST,""""""1"""""",TEST_CLAUSE,TEST @Value(fclass) = farmyard",farmyard
    farmland -> Junction
    farmyard -> Junction
Junction
    -> PointOnAreaOverlayer [AREA]
2016_2016_SISSER (reader SHAPEFILE_12)
    attributes: NM_RAZAO_S varchar(254), CD_PROCESS number(20,0), NR_PROPOST varchar(254), ID_PROPOST long, DT_PROPOST varchar(254), DT_INICIO_ varchar(254), DT_FIM_VIG varchar(254), NM_SEGURAD varchar(254), NR_DOCUMEN varchar(254), NM_MUNICIP varchar(254), SG_UF_PROP varchar(254), LATITUDE varchar(254), NR_GRAU_LA varchar(254), NR_MIN_LAT long, NR_SEG_LAT long, LONGITUDE varchar(254), NR_GRAU_LO varchar(254), NR_MIN_LON long, NR_SEG_LON long, NR_DECIMAL double, NR_DECIM_1 double, NM_CLASSIF varchar(254), NM_CULTURA varchar(254), NR_AREA_TO varchar(254), NR_ANIMAL varchar(254), NR_PRODUTI varchar(254), NR_PRODU_1 varchar(254), NivelDeCob varchar(254), VL_LIMITE_ double, VL_PREMIO_ double,
      PE_TAXA double, VL_SUBVENC double, NR_APOLICE varchar(254), DT_APOLICE varchar(254), ANO_APOLIC varchar(254), CD_GEOCMU varchar(254), VALOR_INDE varchar(254), EVENTO_PRE varchar(254), field_39 varchar(254)
    -> Reprojector_5
2022_SISSER (reader SHAPEFILE_12)
    attributes: NM_RAZAO_S varchar(254), CD_PROCESS number(20,0), NR_PROPOST varchar(254), ID_PROPOST long, DT_PROPOST varchar(254), DT_INICIO_ varchar(254), DT_FIM_VIG varchar(254), NM_SEGURAD varchar(254), NR_DOCUMEN varchar(254), NM_MUNICIP varchar(254), SG_UF_PROP varchar(254), LATITUDE varchar(254), NR_GRAU_LA varchar(254), NR_MIN_LAT varchar(254), NR_SEG_LAT varchar(254), LONGITUDE varchar(254), NR_GRAU_LO varchar(254), NR_MIN_LON varchar(254), NR_SEG_LON varchar(254), NR_DECIMAL double, NR_DECIM_1 double, NM_CLASSIF varchar(254), NM_CULTURA varchar(254), NR_AREA_TO double, NR_ANIMAL varchar(254), NR_PRODUTI double, NR_PRODU_1 double, NivelDeCob varchar(254), VL_LIMITE_ double, VL_PREMIO_ double,
      PE_TAXA double, VL_SUBVENC double, NR_APOLICE varchar(254), DT_APOLICE varchar(254), ANO_APOLIC long, CD_GEOCMU varchar(254)
    -> Reprojector_5
Reprojector_5
    DEST = EPSG:3857
    INTERPOLATION_TYPE_NAME = Nearest Neighbor
    RASTER_CELL_SIZE = Preserve Cells
    RASTER_TOLERANCE = 0.0
    REPROJECTED -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(NM_CULTURA) = Cana-de-açúcar",SUGARCANE
    SUGARCANE -> AttributeManager_4
AttributeManager_4
    ATTR_TABLE:
      REMOVE CD_PROCESS
      REMOVE NR_PROPOST
      REMOVE NR_DOCUMEN
      REMOVE LATITUDE
      REMOVE NR_GRAU_LA
      REMOVE NR_MIN_LAT
      REMOVE NR_SEG_LAT
      REMOVE LONGITUDE
      REMOVE NR_GRAU_LO
      REMOVE NR_MIN_LON
      REMOVE NR_SEG_LON
      REMOVE NR_DECIMAL
      REMOVE NR_DECIM_1
      REMOVE NM_CLASSIF
      REMOVE NR_ANIMAL
      REMOVE NivelDeCob
      REMOVE VL_LIMITE_
      REMOVE VL_PREMIO_
      REMOVE PE_TAXA
      REMOVE VL_SUBVENC
      REMOVE NR_APOLICE
      REMOVE CD_GEOCMU
      REMOVE VALOR_INDE
      REMOVE EVENTO_PRE
      REMOVE field_39
      SET_TO Inicio = @Right(@Value(DT_INICIO_),4)
      SET_TO Fim = @Right(@Value(DT_FIM_VIG),4)
    -> Junction_3
Junction_3
    -> PointOnAreaOverlayer [POINT]
    -> AttributeManager_26
    -> PointOnAreaOverlayer_3 [POINT]
PointOnAreaOverlayer_3
    ATTR_ACCUM_MODE = Merge Incoming
    ATTR_CONFLICT_RES = Use Original
    DEAGGREGATE_INPUT = Yes
    OV_ATTR = _overlaps
    POLYS_FIRST = NO
    AREA -> TestFilter_11
TestFilter_11
    DEFAULT_VALUE = <UNFILTERED>
    PASSED_TEST_GROUP_OUTPUT = FIRST
    TEST_LIST = "BOOL_OP,OR,COMPOSITE_TEST,""""""1"""""",TEST_CLAUSE,TEST @Value(_overlaps) > 0",OSM_SISSER_no_SugarLABLE
    OSM_SISSER_no_SugarLABLE -> Junction_8
Junction_8
    -> AttributeManager_29
    -> Junction_4
AttributeManager_29
    ATTR_TABLE:
      REMOVE full_id
      REMOVE _overlaps
      REMOVE _clipped
    USER_EXPOSED_ATTRIBUTES = osm_id
    -> OSM_SISSER_no_Sugar_Lable (writer SHAPEFILE_27)
OSM_SISSER_no_Sugar_Lable (writer SHAPEFILE_27)
    attributes: NAME_1 varchar(80), NAME_2 varchar(80), NM_RAZAO_S varchar(254), ID_PROPOST long, DT_PROPOST varchar(254), DT_INICIO_ varchar(254), DT_FIM_VIG varchar(254), NM_SEGURAD varchar(254), NM_MUNICIP varchar(254), SG_UF_PROP varchar(254), NM_CULTURA varchar(254), NR_AREA_TO varchar(254), NR_PRODUTI varchar(254), NR_PRODU_1 varchar(254), DT_APOLICE varchar(254), ANO_APOLIC varchar(254), osm_type varchar(254), landuse varchar(254), agricultur varchar(254), crop varchar(254), type varchar(254), fid number(20,0), Inicio varchar(200), Fim varchar(200), osm_id_2 varchar(254), Source varchar(200)
AttributeManager_26
    ATTR_TABLE:
      REMOVE NM_RAZAO_S
      REMOVE ID_PROPOST
      REMOVE DT_PROPOST
      REMOVE DT_INICIO_
      REMOVE DT_FIM_VIG
      REMOVE NM_SEGURAD
      REMOVE NM_MUNICIP
      REMOVE SG_UF_PROP
      REMOVE NM_CULTURA
      REMOVE NR_AREA_TO
      REMOVE NR_PRODUTI
      REMOVE NR_PRODU_1
      REMOVE DT_APOLICE
    -> PointOnAreaOverlayer_2 [POINT]
PointOnAreaOverlayer_2
    ATTR_ACCUM_MODE = Merge Incoming
    ATTR_CONFLICT_RES = Use Original
    DEAGGREGATE_INPUT = Yes
    OV_ATTR = _overlaps
    POLYS_FIRST = NO
    AREA -> TestFilter_8
TestFilter_8
    DEFAULT_VALUE = <UNFILTERED>
    PASSED_TEST_GROUP_OUTPUT = FIRST
    TEST_LIST = "BOOL_OP,OR,COMPOSITE_TEST,""""""1"""""",TEST_CLAUSE,TEST @Value(_overlaps) > 0",Point_Poly,"BOOL_OP,OR,COMPOSITE_TEST,""""""1"""""",TEST_CLAUSE,TEST @Value(_overlaps) = 0",Sugar_noDT
    Point_Poly -> Junction_5
    Sugar_noDT -> AttributeCreator
AttributeCreator
    ATTR_TABLE = SET_TO Sugarcane_no_Date = FME_CONDITIONAL:DEFAULT_VALUE'_FME_NO_OP_'BOOL_OP;OR;COMPOSITE_TEST;1;TEST @Value(_overlaps) = 0'Sugarcane_fields'FME_NUM_CONDITIONS2___
    -> Junction_4
GO_CANA_1011 (reader SHAPEFILE_1)
    attributes: ID long
    -> Reprojector
GO_CANA_1112 (reader SHAPEFILE_2)
    attributes: ID long
    -> Reprojector
MS_CANA_1213 (reader SHAPEFILE_3)
    attributes: ID long
    -> Reprojector
MT_CANA_1213 (reader SHAPEFILE_4)
    attributes: ID long
    -> Reprojector
SP_CANA_1213 (reader SHAPEFILE_5)
    attributes: ID long
    -> Reprojector
Reprojector
    DEST = EPSG:3857
    INTERPOLATION_TYPE_NAME = Nearest Neighbor
    RASTER_CELL_SIZE = Preserve Cells
    RASTER_TOLERANCE = 0.0
    REPROJECTED -> Reprojector_Reprojected
    REPROJECTED -> Generalizer
Generalizer
    ALG_TEXT = NURBfit (Smooth)
    DEGREE = 5
    PRESERVE = No
    PRESERVE_PATHS = No
    SEGMENT_LENGTH = 0
    -> AttributeManager_30
AttributeManager_30
    ATTR_TABLE:
      RENAME_SET_VALUE ID > ID_Conab
      SET_TO Source = Conab
    -> PointOnAreaOverlayer [AREA]
PointOnAreaOverlayer
    ATTR_ACCUM_MODE = Merge Incoming
    ATTR_CONFLICT_RES = Use Original
    DEAGGREGATE_INPUT = Yes
    OV_ATTR = _overlaps
    POLYS_FIRST = NO
    AREA -> AttributeManager
AttributeManager
    ATTR_TABLE = RENAME_SET_VALUE _overlaps > Conab_SISSER
    USER_EXPOSED_ATTRIBUTES = ID
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(Conab_SISSER) > 0",pointpoly
    pointpoly -> AreaCalculator
AreaCalculator
    AREA_ATTR = _area
    AREA_TYPE = Plane Area
    MULT = 0.0001
    -> AttributeRounder
AttributeRounder
    PLACES = 2
    ROUND_TYPE = Nearest
    SRC_ATTRS = _area
    -> Tester
Tester
    BOOL_OP = OR
    TEST_CLAUSE = TEST @Value(_area) < 1000
    TEST_MODE = TEST
    PASSED -> AttributeManager_9
AttributeManager_9
    USER_EXPOSED_ATTRIBUTES = Source,ID
    -> AreaOnAreaOverlayer [AREA]
AreaOnAreaOverlayer
    ACCUM_ATTRS_NAME = Merge Incoming Attributes
    CLEANING_TOLERANCE = Automatic
    CONNECT_Z_MODE = First Wins
    DEAGGREGATE_INPUT = Yes
    GROUP_BY = sfd_id ID_Safra ID_Safrina ID_Conab Id_WorldCereal
    OVC_ATTR = _overlaps
    AREA -> Aggregator_3
Aggregator_3
    ACCUM_ATTRS_NAME = Merge Incoming Attributes
    AGGREGATE_TYPE = Homogeneous Collection (If Possible)
    GROUP_BY = sfd_id ID_Safra ID_Safrina ID_Conab Id_WorldCereal
    MODE = Geometry - Assemble One Level
    SEP = ,
    AGGREGATE -> AttributeManager_8
AttributeManager_8
    -> Junction_5
Junction_5
    -> SpatialRelator [Requestor]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = INTERSECTS
    SUCCESS_ATTR = _related_suppliers
    -> AttributeManager_10
AttributeManager_10
    ATTR_TABLE:
      SET_TO Country = Brazil
      REMOVE sampleID
      REMOVE sfd_id_2
      REMOVE SiteName
      REMOVE LandCover
      REMOVE CropType2
      REMOVE CropType3
      REMOVE Irrigated
      REMOVE Intercrop
      REMOVE Weeding
      REMOVE Area_ha
      REMOVE KeyWords
      REMOVE CT
      REMOVE LC
      REMOVE IRR
      REMOVE usr_idcustomer
      REMOVE frm_name
      REMOVE legacy_id
      REMOVE fld_name
      REMOVE fld_acreage
      REMOVE ssf_plantedarea
      REMOVE ssf_plantedpercentage
      REMOVE esti_emergence
      REMOVE esti_sowing
      REMOVE _overlaps
      REMOVE crp_id
      REMOVE crp_typeid
      REMOVE sfd_sowing
      REMOVE state
      REMOVE area
      REMOVE ID_PROPOST
      REMOVE NM_MUNICIP
      REMOVE SG_UF_PROP
      REMOVE NR_AREA_TO
      REMOVE NR_PRODUTI
      REMOVE NR_PRODU_1
      REMOVE Conab_SISSER
      REMOVE _related_suppliers
      SET_TO Crp_Type = FME_CONDITIONAL:DEFAULT_VALUE'_FME_NO_OP_'BOOL_OP;OR;COMPOSITE_TEST;1 OR 2 OR 3 OR 4 OR 5 OR 6 OR 7;TEST @Value(NM_CULTURA) = Cana-de-açúcar;TEST @Value(CropType1) = Sugarcane;TEST @Value(Landcove_1) = Sugarcane;TEST @Value(crp_code) = SUGARCANE;TEST @Value(crp_type) = SUGARCANE;TEST @Value(fclass) = farmland;TEST @Value(fclass) = farmyard'SUGARCANE'FME_NUM_CONDITIONS2___
    USER_EXPOSED_ATTRIBUTES = ConabSISSER,Id,ID,WorldCereal
    -> AttributeManager_11
AttributeManager_11
    ATTR_TABLE:
      SET_TO Crp_Type = FME_CONDITIONAL:DEFAULT_VALUE'_FME_NO_OP_'BOOL_OP;OR;COMPOSITE_TEST;1 OR 2 OR 3 OR 4 OR 5 OR 6 OR 7;TEST @Value(NM_CULTURA) = Cana-de-açúcar;TEST @Value(CropType1) = Sugarcane;TEST @Value(Landcove_1) = Sugarcane;TEST @Value(crp_code) = SUGARCANE;TEST @Value(crp_type) = SUGARCANE;TEST @Value(fclass) = farmland;TEST @Value(fclass) = farmyard'SUGARCANE'FME_NUM_CONDITIONS2___
      REMOVE NM_CULTURA
      REMOVE CropType1
      REMOVE Landcove_1
      REMOVE crp_code
      REMOVE crp_type
      REMOVE code
      REMOVE fclass
      REMOVE name
      REMOVE _area
    USER_EXPOSED_ATTRIBUTES = ID
    -> Junction_4
Junction_4
    -> AreaCalculator_2
AreaCalculator_2
    AREA_ATTR = _area_2
    AREA_TYPE = Plane Area
    MULT = 0.0001
    -> AttributeRounder_2
AttributeRounder_2
    PLACES = 1
    ROUND_TYPE = Nearest
    SRC_ATTRS = _area_2
    -> TestFilter_13
TestFilter_13
    DEFAULT_VALUE = Others
    PASSED_TEST_GROUP_OUTPUT = FIRST
    TEST_LIST = "BOOL_OP,OR,COMPOSITE_TEST,""""""1"""""",TEST_CLAUSE,TEST @Value(Source) = WorldCereal",WorldCereal,"BOOL_OP,OR,COMPOSITE_TEST,""""""1"""""",TEST_CLAUSE,TEST @Value(Source) = GEOSYS",GEOSYS,"BOOL_OP,OR,COMPOSITE_TEST,""""""1"""""",TEST_CLAUSE,TEST @Value(Source) = OSM_2",OSM_2,"BOOL_OP,OR,COMPOSITE_TEST,""""""1"""""",TEST_CLAUSE,TEST @Value(Source) = TOKIO_MARINE",TOKIO_MARINE1,"BOOL_OP,OR,COMPOSITE_TEST,""""""1"""""",TEST_CLAUSE,TEST @Value(Source) = MAPFRE",MAPFRE,"BOOL_OP,OR,COMPOSITE_TEST,""""""1"""""",TEST_CLAUSE,TEST @Value(Source) = SICOOB",SICOOB,"BOOL_OP,OR,COMPOSITE_TEST,""""""1"""""",TEST_CLAUSE,TEST @Value(Source) = CASARI",CASARI,"BOOL_OP,OR,COMPOSITE_TEST,""""""1"""""",TEST_CLAUSE,TEST @Value(Source) = BENDZIUS",BENDZIUS
    WorldCereal -> Aggregator_4
    GEOSYS -> Aggregator_5
    OSM_2 -> Aggregator_6
    TOKIO_MARINE1 -> Aggregator_7
    MAPFRE -> Aggregator_8
    SICOOB -> Aggregator_9
    CASARI -> Aggregator_10
    BENDZIUS -> Aggregator_11
    Others -> Aggregator_12
Aggregator_4
    ACCUM_ATTRS_NAME = Merge Incoming Attributes
    AGGREGATE_TYPE = Homogeneous Collection (If Possible)
    GROUP_BY = Id_WorldCereal
    MODE = Geometry - Assemble One Level
    SEP = ,
    AGGREGATE -> AttributeManager_34
Aggregator_5
    ACCUM_ATTRS_NAME = Merge Incoming Attributes
    AGGREGATE_TYPE = Homogeneous Collection (If Possible)
    GROUP_BY = ID_Safra ID_Safrina sfd_id
    MODE = Geometry - Assemble One Level
    SEP = ,
    AGGREGATE -> AttributeManager_34
AttributeManager_34
    ATTR_TABLE = SET_TO QC = 1
    -> Junction_9
Aggregator_6
    ACCUM_ATTRS_NAME = Merge Incoming Attributes
    AGGREGATE_TYPE = Homogeneous Collection (If Possible)
    GROUP_BY = osm_id_2
    MODE = Geometry - Assemble One Level
    SEP = ,
    AGGREGATE -> TestFilter_14
Aggregator_7
    ACCUM_ATTRS_NAME = Merge Incoming Attributes
    AGGREGATE_TYPE = Homogeneous Collection (If Possible)
    GROUP_BY = ID_Safra ID_Safrina sfd_id
    MODE = Geometry - Assemble One Level
    SEP = ,
    AGGREGATE -> TestFilter_14
Aggregator_8
    ACCUM_ATTRS_NAME = Merge Incoming Attributes
    AGGREGATE_TYPE = Homogeneous Collection (If Possible)
    GROUP_BY = ID_Safra ID_Safrina sfd_id
    MODE = Geometry - Assemble One Level
    SEP = ,
    AGGREGATE -> TestFilter_14
Aggregator_9
    ACCUM_ATTRS_NAME = Merge Incoming Attributes
    AGGREGATE_TYPE = Homogeneous Collection (If Possible)
    GROUP_BY = ID_Safra ID_Safrina sfd_id
    MODE = Geometry - Assemble One Level
    SEP = ,
    AGGREGATE -> TestFilter_14
Aggregator_10
    ACCUM_ATTRS_NAME = Merge Incoming Attributes
    AGGREGATE_TYPE = Homogeneous Collection (If Possible)
    GROUP_BY = ID_Safra ID_Safrina sfd_id
    MODE = Geometry - Assemble One Level
    SEP = ,
    AGGREGATE -> TestFilter_14
Aggregator_11
    ACCUM_ATTRS_NAME = Merge Incoming Attributes
    AGGREGATE_TYPE = Homogeneous Collection (If Possible)
    GROUP_BY = ID_Safra ID_Safrina sfd_id
    MODE = Geometry - Assemble One Level
    SEP = ,
    AGGREGATE -> TestFilter_14
TestFilter_14
    DEFAULT_VALUE = <UNFILTERED>
    PASSED_TEST_GROUP_OUTPUT = FIRST
    TEST_LIST = "BOOL_OP,OR,COMPOSITE_TEST,""""""1"""""",TEST_CLAUSE,TEST @Value(_area_2) >= 5",>5
    >5 -> AttributeManager_33
    <UNFILTERED> -> AttributeManager_32
AttributeManager_33
    ATTR_TABLE = SET_TO QC = 1
    -> Junction_9
AttributeManager_32
    ATTR_TABLE = SET_TO QC = 0
    -> Junction_9
Junction_9
    -> Junction_10
Aggregator_12
    ACCUM_ATTRS_NAME = Merge Incoming Attributes
    AGGREGATE_TYPE = Homogeneous Collection (If Possible)
    GROUP_BY = ID_Conab osm_id
    MODE = Geometry - Assemble One Level
    SEP = ,
    AGGREGATE -> TestFilter_12
TestFilter_12
    DEFAULT_VALUE = In_Between
    PASSED_TEST_GROUP_OUTPUT = FIRST
    TEST_LIST = "BOOL_OP,OR,COMPOSITE_TEST,""""""1"""""",TEST_CLAUSE,TEST @Value(_area_2) >= 1000",>1000,"BOOL_OP,OR,COMPOSITE_TEST,""""""1"""""",TEST_CLAUSE,TEST @Value(_area_2) < 25",<25
    <25 -> AttributeManager_36
    In_Between -> AttributeManager_35
AttributeManager_36
    ATTR_TABLE = SET_TO QC = 0
    -> Junction_10
AttributeManager_35
    ATTR_TABLE = SET_TO QC = 1
    -> Junction_10
Junction_10
    -> AttributeCreator_2
AttributeCreator_2
    ATTR_TABLE:
      SET_TO SSS = @Value(Inicio)@Value(sfd_swg)@Value(Sow_W)@Value(sowing)
      SET_TO HHH = @Value(Fim)@Value(harvest)@Value(Harvest_W)@Value(sfd_swg_2)
    -> AttributeManager_31
AttributeManager_31
    ATTR_TABLE:
      SET_TO ID = @Value(ID_Conab)@Value(ID_Safra)@Value(ID_Safrina)@Value(Id_WorldCereal)@Value(osm_id)@Value(osm_id_2)@Value(sfd_id)
      SET_TO crp_code = SUGARCANE
      SET_TO crp_id = 13
      SET_TO crp_typeid = 5
      RENAME_SET_VALUE sfd_sowingdate > sfd_sowing
      REMOVE sowing
      RENAME_SET_VALUE SSS > SOWING
      RENAME_SET_VALUE HHH > HARVEST
      REMOVE harvest
      RENAME_SET_VALUE NAME_1 > State
      RENAME_SET_VALUE _area_2 > area
      REMOVE Inicio
      REMOVE Fim
      REMOVE Sow_W
      REMOVE Harvest_W
      REMOVE sfd_swg
      REMOVE sfd_swg_2
    -> AttributeManager_37
AttributeManager_37
    ATTR_TABLE:
      REMOVE unique_id
      SET_TO Crp_Type = SUGARCANE
      REMOVE Country
      REMOVE NAME_2
      REMOVE fid
      REMOVE sfd_id
      REMOVE date_part
      REMOVE AcquiDate
      REMOVE ANO_APOLIC
      REMOVE DT_APOLICE
      REMOVE valtime
      REMOVE ssf_season
      REMOVE DT_PROPOST
      REMOVE DT_INICIO_
      REMOVE DT_FIM_VIG
      REMOVE DataSource
      REMOVE source
      REMOVE cst_code
      REMOVE SOS
      REMOVE EOS
      REMOVE sfd_geometry
      REMOVE NM_RAZAO_S
      REMOVE NM_SEGURAD
      REMOVE osm_id
      REMOVE crop
      REMOVE Sugarcane_no_Date
      REMOVE _overlaps
      REMOVE ID_PROPOST
      REMOVE NM_MUNICIP
      REMOVE SG_UF_PROP
      REMOVE NM_CULTURA
      REMOVE NR_AREA_TO
      REMOVE NR_PRODUTI
      REMOVE NR_PRODU_1
      REMOVE full_id
      REMOVE osm_type
      REMOVE landuse
      REMOVE agricultural
      REMOVE type
      REMOVE _clipped
      REMOVE ID_Conab
      REMOVE ID_Safrina
      REMOVE ID_Safra
      REMOVE Id_WorldCereal
      REMOVE osm_id_2
    -> Reprojector_3
Reprojector_3
    DEST = EPSG:4326
    INTERPOLATION_TYPE_NAME = Nearest Neighbor
    RASTER_CELL_SIZE = Preserve Cells
    RASTER_TOLERANCE = 0.0
    REPROJECTED -> Junction_18
Junction_18
    -> TestFilter_5
    -> TestFilter_15
    -> All (writer SHAPEFILE_31)
TestFilter_15
    DEFAULT_VALUE = Others
    PASSED_TEST_GROUP_OUTPUT = FIRST
    TEST_LIST = "BOOL_OP,OR,COMPOSITE_TEST,""""""1"""""",TEST_CLAUSE,TEST @Value(Source) = WorldCereal",WorldCereal,"BOOL_OP,OR,COMPOSITE_TEST,""""""1"""""",TEST_CLAUSE,TEST @Value(Source) = GEOSYS",GEOSYS
    WorldCereal -> AttributeManager_12
    GEOSYS -> AttributeManager_12
    Others -> Tester_2
Tester_2
    BOOL_OP = COMPOSITE
    COMPOSITE_TEST = 1 AND 2
    TEST_CLAUSE:
      TEST @Value(area) >= 25
      TEST @Value(area) <= 1000
    TEST_MODE = TEST
    PASSED -> TestFilter_16
TestFilter_16
    DEFAULT_VALUE = NoDate
    PASSED_TEST_GROUP_OUTPUT = FIRST
    TEST_LIST = "BOOL_OP,OR,COMPOSITE_TEST,""""""1"""""",TEST_CLAUSE,TEST SOWING ATTRIBUTE_HAS_A_VALUE """,Date
    Date -> AttributeManager_12
AttributeManager_12
    -> SUGARCANE (writer SHAPEFILE_30)
    -> Tester_3
SUGARCANE (writer SHAPEFILE_30)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
Tester_3
    BOOL_OP = AND
    TEST_CLAUSE:
      TEST @Value(SOWING) != 2016
      TEST @Value(SOWING) != 2017
    TEST_MODE = TEST
    PASSED -> ALL (writer SHAPEFILE_32)
ALL (writer SHAPEFILE_32)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
TestFilter_5
    DEFAULT_VALUE = <UNFILTERED>
    PASSED_TEST_GROUP_OUTPUT = FIRST
    TEST_LIST = "BOOL_OP,OR,COMPOSITE_TEST,""""""1"""""",TEST_CLAUSE,TEST @Value(SOWING) = 2016",2016,"BOOL_OP,OR,COMPOSITE_TEST,""""""1"""""",TEST_CLAUSE,TEST @Value(SOWING) = 2017",2017,"BOOL_OP,OR,COMPOSITE_TEST,""""""1"""""",TEST_CLAUSE,TEST @Value(SOWING) = 2018",2018,"BOOL_OP,OR,COMPOSITE_TEST,""""""1"""""",TEST_CLAUSE,TEST @Value(SOWING) = 2019",2019,"BOOL_OP,OR,COMPOSITE_TEST,""""""1"""""",TEST_CLAUSE,TEST @Value(SOWING) = 2020",2020,"BOOL_OP,OR,COMPOSITE_TEST,""""""1"""""",TEST_CLAUSE,TEST @Value(SOWING) = 2021",2021,"BOOL_OP,OR,COMPOSITE_TEST,""""""1"""""",TEST_CLAUSE,TEST @Value(SOWING) = 2022",2022,"BOOL_OP,OR,COMPOSITE_TEST,""""""1"""""",TEST_CLAUSE,TEST @Value(SOWING) = 2023",2023,"BOOL_OP,OR,COMPOSITE_TEST,""""""1"""""",TEST_CLAUSE,TEST SOWING ATTRIBUTE_IS_EMPTY """,Sugarcane_no_Date
    2016 -> AttributeManager_39
    2017 -> AttributeManager_38
    2018 -> AttributeManager_17
    2019 -> AttributeManager_18
    2020 -> AttributeManager_19
    2021 -> AttributeManager_20
    2022 -> AttributeManager_21
    Sugarcane_no_Date -> RandomNumberGenerator
    <UNFILTERED> -> Other (writer SHAPEFILE_11)
AttributeManager_39
    -> Junction_11
Junction_11
    -> 2016 (writer SHAPEFILE_28)
    -> Matcher
2016 (writer SHAPEFILE_28)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
AttributeManager_38
    -> Junction_12
Junction_12
    -> 2017 (writer SHAPEFILE_29)
    -> Matcher
2017 (writer SHAPEFILE_29)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
AttributeManager_17
    USER_EXPOSED_ATTRIBUTES = ID,crp_code,crp_id,Crp_Type,crp_typeid,sfd_sowing,SOWING,HARVEST,season,State,Source,area,QC,ml_split
    -> Junction_13
Junction_13
    -> 2018 (writer SHAPEFILE_14)
    -> Matcher
    -> AttributeManager_12_Output
AttributeManager_12_Output: Inspector
2018 (writer SHAPEFILE_14)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
AttributeManager_18
    USER_EXPOSED_ATTRIBUTES = ID,crp_code,crp_id,Crp_Type,crp_typeid,sfd_sowing,SOWING,HARVEST,season,State,Source,area,QC,ml_split
    -> Junction_14
Junction_14
    -> 2019 (writer SHAPEFILE_15)
    -> AttributeManager_13_Output
    -> Matcher
AttributeManager_13_Output: Inspector
2019 (writer SHAPEFILE_15)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
AttributeManager_19
    USER_EXPOSED_ATTRIBUTES = ID,crp_code,crp_id,Crp_Type,crp_typeid,sfd_sowing,SOWING,HARVEST,season,State,Source,area,QC,ml_split
    -> Junction_15
Junction_15
    -> 2020 (writer SHAPEFILE_16)
    -> AttributeManager_14_Output
    -> Matcher
AttributeManager_14_Output: Inspector
2020 (writer SHAPEFILE_16)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
AttributeManager_20
    USER_EXPOSED_ATTRIBUTES = ID,crp_code,crp_id,Crp_Type,crp_typeid,sfd_sowing,SOWING,HARVEST,season,State,Source,area,QC,ml_split
    -> Junction_16
Junction_16
    -> 2021 (writer SHAPEFILE_17)
    -> AttributeManager_15_Output
    -> Matcher
AttributeManager_15_Output: Inspector
2021 (writer SHAPEFILE_17)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
AttributeManager_21
    USER_EXPOSED_ATTRIBUTES = ID,crp_code,crp_id,Crp_Type,crp_typeid,sfd_sowing,SOWING,HARVEST,season,State,Source,area,QC,ml_split
    -> Junction_17
Junction_17
    -> 2022 (writer SHAPEFILE_18)
    -> AttributeManager_16_Output
    -> Matcher
AttributeManager_16_Output: Inspector
2022 (writer SHAPEFILE_18)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
Other (writer SHAPEFILE_11)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
RandomNumberGenerator
    MAX = 10
    MIN = 0
    PLACES = 0
    RESULT_ATTR = _random_number
    -> AttributeManager_27
AttributeManager_27
    USER_EXPOSED_ATTRIBUTES = ID,crp_code,crp_id,Crp_Type,crp_typeid,sfd_sowing,SOWING,HARVEST,season,State,Source,area,QC,ml_split
    -> Sugarcane_Fields_No_DT (writer SHAPEFILE_24)
    -> Matcher
Matcher
    BLANK_AND_MISSING_NAMES_TRAITS_DIFFER = Yes
    CHECK_COORDINATE_SYSTEMS = No
    LENIENT_MATCH = No
    MATCH = FULL
    MATCHED -> Matcher_Matched
    SINGLE_MATCHED -> Matcher_SingleMatched
    NOT_MATCHED -> Matcher_NotMatched
Matcher_Matched: Inspector
Matcher_SingleMatched: Inspector
Matcher_NotMatched: Inspector
Sugarcane_Fields_No_DT (writer SHAPEFILE_24)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0), Q__random_ double
All (writer SHAPEFILE_31)
    attributes: ID varchar(200), crp_code varchar(200), crp_id varchar(200), Crp_Type varchar(200), crp_typeid varchar(200), sfd_sowing date, SOWING varchar(200), HARVEST varchar(200), season varchar(254), State varchar(80), Source varchar(200), area double, QC number(20,0), ml_split number(20,0)
Reprojector_Reprojected: Inspector
USINAS_CANA_BR_ATIVAS_2021 (reader SHAPEFILE_25)
    attributes: UF varchar(254), UNIDADE varchar(254), PERFIL varchar(254), LATITUDE double, LONGITUDE double, ID long
    -> Reprojector_11
Reprojector_11
    DEST = EPSG:3857
    INTERPOLATION_TYPE_NAME = Nearest Neighbor
    RASTER_CELL_SIZE = Preserve Cells
    RASTER_TOLERANCE = 0.0
    REPROJECTED -> Bufferer
Bufferer
    ANGLE = 22.5
    CAP_STYLE = Arc
    CORNER_STYLE = Arc
    MODE = AREA
    OFFSET = 10
    OFFSET_UNITS = KM
    PRECISION = APPROX
    BUFFERED -> AreaOnAreaOverlayer_3 [AREA]
AreaOnAreaOverlayer_3
    ACCUM_ATTRS_NAME = Merge Incoming Attributes
    CLEANING_TOLERANCE = Automatic
    CONNECT_Z_MODE = First Wins
    DEAGGREGATE_INPUT = Yes
    OVC_ATTR = _overlaps
    AREA -> Dissolver
Dissolver
    ACCUM_INPUT_ATTRS = Merge Incoming Attributes
    CLEANING_TOLERANCE = Automatic
    CONNECT_Z_MODE = First Wins
    DEAGGREGATE_INPUT = Yes
    GROUP_BY = osm_id_2
    AREA -> TestFilter_10
TestFilter_10
    DEFAULT_VALUE = <UNFILTERED>
    PASSED_TEST_GROUP_OUTPUT = FIRST
    TEST_LIST:
      "BOOL_OP,AND,COMPOSITE_TEST,""""""1 AND 2"""""",TEST_CLAUSE,TEST ID ATTRIBUTE_HAS_A_VALUE ""
      TEST osm_id ATTRIBUTE_HAS_A_VALUE """,Raduis_10
    Raduis_10 -> AttributeManager_28
AttributeManager_28
    ATTR_TABLE:
      REMOVE full_id
      REMOVE _clipped
      REMOVE _overlaps
    USER_EXPOSED_ATTRIBUTES = osm_id
    -> OSM_Usine (writer SHAPEFILE_26)
OSM_Usine (writer SHAPEFILE_26)
    attributes: NAME_1 varchar(80), NAME_2 varchar(80), ID long, UF varchar(254), UNIDADE varchar(254), PERFIL varchar(254), LATITUDE double, LONGITUDE double, osm_type varchar(254), landuse varchar(254), agricultur varchar(254), crop varchar(254), type varchar(254), fid number(20,0), osm_id_2 varchar(254), Source varchar(200)
