FME workspace Manicipality_selection.fmw

Parameters:
- SourceDataset_OGCGEOPACKAGE = ""$(FME_MF_DIR)Sao_Paulo\*.gpkg" "$(FME_MF_DIR)Parana\*.gpkg""   # GeoPackage File
- FEATURE_TYPES =
- SourceDataset_SHAPEFILE = C:\Users\lyi\Desktop\Brazil_Crop_ID\Input_Data_2\gadm36_BRA_shp\gadm36_BRA_2.shp   # Source Esri Shapefile(s)
- FEATURE_TYPES_2 =
- SourceDataset_SHAPEFILE_3 = C:\Users\lyi\Desktop\Brazil_Crop_ID\Selection_CropID\AllCrop.shp   # Source Esri Shapefile(s)
- FEATURE_TYPES_3 =
- DestDataset_SHAPEFILE_2 = $(FME_MF_DIR)Result\DL_outputs\v2   # Destination Esri Shapefile Folder
- DestDataset_SHAPEFILE_6 = $(FME_MF_DIR)Result\DL_outputs\sowing_year_2022   # Destination Esri Shapefile Folder
- DestDataset_SHAPEFILE = $(FME_MF_DIR)Result\GrounData\sowing_2022   # Destination Esri Shapefile Folder

Readers:
- OGCGEOPACKAGE_1: OGCGEOPACKAGE from $(SourceDataset_OGCGEOPACKAGE)
- SHAPEFILE_1: SHAPEFILE from $(SourceDataset_SHAPEFILE)
- SHAPEFILE_2: SHAPEFILE from $(SourceDataset_SHAPEFILE_3)

Writers:
- SHAPEFILE_3: SHAPEFILE to $(DestDataset_SHAPEFILE)
- SHAPEFILE_4: SHAPEFILE to $(DestDataset_SHAPEFILE_2)
- SHAPEFILE_5: SHAPEFILE to $(DestDataset_SHAPEFILE_6)

AllCrop (reader SHAPEFILE_2)
    attributes: ID varchar(200), crp_code varchar(254), crp_id number(31,15), crp_type varchar(254), crp_typeid number(31,15), sfd_sowing varchar(254), sowing varchar(254), harvest varchar(254), season varchar(254), state varchar(254), source varchar(254), area number(31,15), ml_split varchar(200), QC number(31,15), layer varchar(254), path varchar(254)
    -> Tester_3
Tester_3
    BOOL_OP = AND
    TEST_CLAUSE:
      TEST @Value(QC) = 1
      TEST @Value(sowing) = 2022
    TEST_MODE = TEST
    PASSED -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(state) = SAO PAULO",SAO PAULO,"BOOL_OP,OR,COMPOSITE_TEST,""""""1"""""",TEST_CLAUSE,TEST @Value(state) = PARANA",PARANA
    SAO PAULO -> Reprojector_3
    PARANA -> Reprojector_3
Reprojector_3
    DEST = EPSG:4326
    INTERPOLATION_TYPE_NAME = Nearest Neighbor
    RASTER_CELL_SIZE = Preserve Cells
    RASTER_TOLERANCE = 0.0
    REPROJECTED -> SpatialRelator [Requestor]
gadm36_BRA_2 (reader SHAPEFILE_1)
    attributes: GID_0 varchar(80), NAME_0 varchar(80), GID_1 varchar(80), NAME_1 varchar(80), NL_NAME_1 varchar(80), GID_2 varchar(80), NAME_2 varchar(80), VARNAME_2 varchar(80), NL_NAME_2 varchar(80), TYPE_2 varchar(80), ENGTYPE_2 varchar(80), CC_2 varchar(80), HASC_2 varchar(80)
    -> Tester_2
Tester_2
    BOOL_OP = OR
    TEST_CLAUSE:
      TEST @Value(NAME_1) = São Paulo
      TEST @Value(NAME_1) = Paraná
    TEST_MODE = TEST
    PASSED -> Reprojector_2
Reprojector_2
    DEST = EPSG:4326
    INTERPOLATION_TYPE_NAME = Nearest Neighbor
    RASTER_CELL_SIZE = Preserve Cells
    RASTER_TOLERANCE = 0.0
    REPROJECTED -> SpatialRelator [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    LIST_NAME = _relationships
    PREDICATES = WITHIN INTERSECTS
    SUCCESS_ATTR = _related_suppliers
    -> Tester_4
Tester_4
    BOOL_OP = OR
    TEST_CLAUSE:
      TEST @Value(NAME_1) = São Paulo
      TEST @Value(NAME_1) = Paraná
    TEST_MODE = TEST
    PASSED -> StatisticsCalculator
StatisticsCalculator
    CALCULATION_MODE = NUMERIC
    FEAT_STATS = ID,NUMERIC_MODE,,,COUNT,,,,,,,,,,
    GROUP_BY = NAME_2
    COMPLETE -> Sorter
Sorter
    SORT_PARM = ID.total_count NUMERIC DESCENDING
    SORTED -> Sorter_Sorted
    SORTED -> AttributeManager
Sorter_Sorted: Inspector
AttributeManager
    ATTR_TABLE:
      REMOVE layer
      REMOVE path
      REMOVE fme_feature_type
      REMOVE GID_0
      REMOVE NAME_0
      REMOVE GID_1
      REMOVE NAME_1
      REMOVE NL_NAME_1
      REMOVE GID_2
      REMOVE VARNAME_2
      REMOVE NL_NAME_2
      REMOVE TYPE_2
      REMOVE ENGTYPE_2
      REMOVE CC_2
      REMOVE HASC_2
      REMOVE _relationships{}.de9im
      REMOVE _relationships{}.pass{}
      REMOVE _related_suppliers
      REMOVE ID.total_count
    -> All_types (writer SHAPEFILE_3)
All_types (writer SHAPEFILE_3)
    attributes: ID varchar(200), crp_code varchar(254), crp_id number(31,15), crp_type varchar(254), crp_typeid number(31,15), sfd_sowing varchar(254), sowing varchar(254), harvest varchar(254), season varchar(254), state varchar(254), source varchar(254), area number(31,15), ml_split varchar(200), QC number(31,15), NAME_2 varchar(80)
DL_fieldborders_BRA.20.136_Brazil_Rio-Grande-do-Norte_Sao-Paulo-do-Potengi_EDA (reader OGCGEOPACKAGE_1)
    attributes: Geosys_Id text(200), area double, perimeter double, GID_2 text(254), COUNTRY text(254), GID_0 text(254), GID_1 text(254), NAME_1 text(254), NAME_2 text(254), pathDLfile text(50), DN text(254), fid int,PrimaryKey
    -> Tester
Tester
    BOOL_OP = OR
    TEST_CLAUSE:
      TEST @Value(NAME_1) = Sao-Paulo
      TEST @Value(NAME_1) = Parana
    TEST_MODE = TEST
    PASSED -> Reprojector
Reprojector
    DEST = EPSG:4326
    INTERPOLATION_TYPE_NAME = Nearest Neighbor
    RASTER_CELL_SIZE = Preserve Cells
    RASTER_TOLERANCE = 0.0
    REPROJECTED -> Junction
Junction
    -> TestFilter
    -> TestFilter_3
TestFilter
    DEFAULT_VALUE = <UNFILTERED>
    PASSED_TEST_GROUP_OUTPUT = FIRST
    TEST_LIST = "BOOL_OP,OR,COMPOSITE_TEST,""""""1"""""",TEST_CLAUSE,TEST @Value(NAME_2) = Itabera",Itabera,"BOOL_OP,OR,COMPOSITE_TEST,""""""1"""""",TEST_CLAUSE,TEST @Value(NAME_2) = Jacarezinho",Jacarezinho,"BOOL_OP,OR,COMPOSITE_TEST,""""""1"""""",TEST_CLAUSE,TEST @Value(NAME_2) = Terra-Roxa",Terra Roxa,"BOOL_OP,OR,COMPOSITE_TEST,""""""1"""""",TEST_CLAUSE,TEST @Value(NAME_2) = Itapeva",Itapeva,"BOOL_OP,OR,COMPOSITE_TEST,""""""1"""""",TEST_CLAUSE,TEST @Value(NAME_2) = Taquarituba",Taquarituba,"BOOL_OP,OR,COMPOSITE_TEST,""""""1"""""",TEST_CLAUSE,TEST @Value(NAME_2) = Cambara",Cambara,"BOOL_OP,OR,COMPOSITE_TEST,""""""1"""""",TEST_CLAUSE,TEST @Value(NAME_2) = Marilena",Marilena,"BOOL_OP,OR,COMPOSITE_TEST,""""""1"""""",TEST_CLAUSE,TEST @Value(NAME_2) = Sao-Manoel-do-Parana",Sao Manoel do Parana,"BOOL_OP,OR,COMPOSITE_TEST,""""""1"""""",TEST_CLAUSE,TEST @Value(NAME_2) = Penapolis",Penapolis,"BOOL_OP,OR,COMPOSITE_TEST,""""""1"""""",TEST_CLAUSE,TEST @Value(NAME_2) = Itai",Itai,"BOOL_OP,OR,COMPOSITE_TEST,""""""1"""""",TEST_CLAUSE,TEST @Value(NAME_2) = Itarare",Itarare,"BOOL_OP,OR,COMPOSITE_TEST,""""""1"""""",TEST_CLAUSE,TEST @Value(NAME_2) = Tuneiras-do-Oeste",Tuneiras do Oeste,"BOOL_OP,OR,COMPOSITE_TEST,""""""1"""""",TEST_CLAUSE,TEST @Value(NAME_2) = Londrina",Londrina,"BOOL_OP,OR,COMPOSITE_TEST,""""""1"""""",TEST_CLAUSE,TEST @Value(NAME_2) = Coronel-Macedo",Coronel Macedo,"BOOL_OP,OR,COMPOSITE_TEST,""""""1"""""",TEST_CLAUSE,TEST @Value(NAME_2) = Panorama",Panorama,"BOOL_OP,OR,COMPOSITE_TEST,""""""1"""""",TEST_CLAUSE,TEST @Value(NAME_2) = Itambe",Itambe,"BOOL_OP,OR,COMPOSITE_TEST,""""""1"""""",TEST_CLAUSE,TEST @Value(NAME_2) = Cascavel",Cascavel,"BOOL_OP,OR,COMPOSITE_TEST,""""""1"""""",TEST_CLAUSE,TEST @Value(NAME_2) = Sao-Tome",Sao Tome,"BOOL_OP,OR,COMPOSITE_TEST,""""""1"""""",TEST_CLAUSE,TEST @Value(NAME_2) = Pirai-do-Sul",Pirai do Sul,"BOOL_OP,OR,COMPOSITE_TEST,""""""1"""""",TEST_CLAUSE,TEST @Value(NAME_2) = Pitangueiras",Pitangueiras,"BOOL_OP,OR,COMPOSITE_TEST,""""""1"""""",TEST_CLAUSE,TEST @Value(NAME_2) = Cruzeiro-do-Sul",Cruzeiro do Sul,"BOOL_OP,OR,COMPOSITE_TEST,""""""1"""""",TEST_CLAUSE,TEST @Value(NAME_2) = Guaira",Guaira,"BOOL_OP,OR,COMPOSITE_TEST,""""""1"""""",TEST_CLAUSE,TEST @Value(NAME_2) = Ortigueira",Ortigueira,"BOOL_OP,OR,COMPOSITE_TEST,""""""1"""""",TEST_CLAUSE,TEST @Value(NAME_2) = Toledo",Toledo,"BOOL_OP,OR,COMPOSITE_TEST,""""""1"""""",TEST_CLAUSE,TEST @Value(NAME_2) = Mambore",Mambore,"BOOL_OP,OR,COMPOSITE_TEST,""""""1"""""",TEST_CLAUSE,TEST @Value(NAME_2) = Lobato",Lobato
    Itabera -> DL_output (writer SHAPEFILE_4)
    Itabera -> HullReplacer
    Jacarezinho -> DL_output (writer SHAPEFILE_4)
    Terra Roxa -> DL_output (writer SHAPEFILE_4)
    Terra Roxa -> HullReplacer
    Itapeva -> DL_output (writer SHAPEFILE_4)
    Taquarituba -> DL_output (writer SHAPEFILE_4)
    Cambara -> DL_output (writer SHAPEFILE_4)
    Marilena -> DL_output (writer SHAPEFILE_4)
    Sao Manoel do Parana -> DL_output (writer SHAPEFILE_4)
    Penapolis -> DL_output (writer SHAPEFILE_4)
    Itai -> DL_output (writer SHAPEFILE_4)
    Itarare -> DL_output (writer SHAPEFILE_4)
    Tuneiras do Oeste -> DL_output (writer SHAPEFILE_4)
    Londrina -> DL_output (writer SHAPEFILE_4)
    Coronel Macedo -> DL_output (writer SHAPEFILE_4)
    Panorama -> DL_output (writer SHAPEFILE_4)
    Itambe -> DL_output (writer SHAPEFILE_4)
    Cascavel -> DL_output (writer SHAPEFILE_4)
    Sao Tome -> DL_output (writer SHAPEFILE_4)
    Pirai do Sul -> DL_output (writer SHAPEFILE_4)
    Pitangueiras -> DL_output (writer SHAPEFILE_4)
    Cruzeiro do Sul -> DL_output (writer SHAPEFILE_4)
    Guaira -> DL_output (writer SHAPEFILE_4)
    Guaira -> HullReplacer
    Ortigueira -> DL_output (writer SHAPEFILE_4)
    Toledo -> DL_output (writer SHAPEFILE_4)
    Mambore -> DL_output (writer SHAPEFILE_4)
    Mambore -> HullReplacer
    Lobato -> DL_output (writer SHAPEFILE_4)
    Lobato -> HullReplacer
HullReplacer
    3DMODE_PARAM = Automatic
    HULLTYPE_PARAM = Concave )(
    HULL -> HullReplacer_Hull
    HULL -> DL_output00 (writer SHAPEFILE_4)
DL_output00 (writer SHAPEFILE_4)
    attributes: Geosys_Id varchar(200), area double, perimeter double, GID_2 varchar(254), COUNTRY varchar(254), GID_0 varchar(254), GID_1 varchar(254), NAME_1 varchar(254), NAME_2 varchar(254), pathDLfile varchar(50), DN varchar(254), fid number(20,0)
HullReplacer_Hull: Inspector
DL_output (writer SHAPEFILE_4)
    attributes: Geosys_Id varchar(200), area double, perimeter double, GID_2 varchar(254), COUNTRY varchar(254), GID_0 varchar(254), GID_1 varchar(254), NAME_1 varchar(254), NAME_2 varchar(254), pathDLfile varchar(50), DN varchar(254), fid number(20,0)
TestFilter_3
    DEFAULT_VALUE = <UNFILTERED>
    PASSED_TEST_GROUP_OUTPUT = FIRST
    TEST_LIST = "BOOL_OP,OR,COMPOSITE_TEST,""""""1"""""",TEST_CLAUSE,TEST @Value(NAME_2) = Itabera",Itabera,"BOOL_OP,OR,COMPOSITE_TEST,""""""1"""""",TEST_CLAUSE,TEST @Value(NAME_2) = Itapeva",Itapeva,"BOOL_OP,OR,COMPOSITE_TEST,""""""1"""""",TEST_CLAUSE,TEST @Value(NAME_2) = Taquarituba",Taquarituba,"BOOL_OP,OR,COMPOSITE_TEST,""""""1"""""",TEST_CLAUSE,TEST @Value(NAME_2) = Itai",Itai,"BOOL_OP,OR,COMPOSITE_TEST,""""""1"""""",TEST_CLAUSE,TEST @Value(NAME_2) = Londrina",Londrina,"BOOL_OP,OR,COMPOSITE_TEST,""""""1"""""",TEST_CLAUSE,TEST @Value(NAME_2) = Coronel-Macedo",Coronel Macedo,"BOOL_OP,OR,COMPOSITE_TEST,""""""1"""""",TEST_CLAUSE,TEST @Value(NAME_2) = Ortigueira",Ortigueira,"BOOL_OP,OR,COMPOSITE_TEST,""""""1"""""",TEST_CLAUSE,TEST @Value(NAME_2) = Ivate",Ivate,"BOOL_OP,OR,COMPOSITE_TEST,""""""1"""""",TEST_CLAUSE,TEST @Value(NAME_2) = Sertanopolis",Sertanopolis,"BOOL_OP,OR,COMPOSITE_TEST,""""""1"""""",TEST_CLAUSE,TEST @Value(NAME_2) = Pinhao",Pinhao
    Itabera -> AllCrop (writer SHAPEFILE_5)
    Itapeva -> AllCrop (writer SHAPEFILE_5)
    Taquarituba -> AllCrop (writer SHAPEFILE_5)
    Ivate -> AllCrop (writer SHAPEFILE_5)
    Itai -> AllCrop (writer SHAPEFILE_5)
    Sertanopolis -> AllCrop (writer SHAPEFILE_5)
    Pinhao -> AllCrop (writer SHAPEFILE_5)
    Londrina -> AllCrop (writer SHAPEFILE_5)
    Coronel Macedo -> AllCrop (writer SHAPEFILE_5)
    Ortigueira -> AllCrop (writer SHAPEFILE_5)
AllCrop (writer SHAPEFILE_5)
    attributes: Geosys_Id varchar(200), area double, perimeter double, GID_2 varchar(254), COUNTRY varchar(254), GID_0 varchar(254), GID_1 varchar(254), NAME_1 varchar(254), NAME_2 varchar(254), pathDLfile varchar(50), DN varchar(254), fid number(20,0)
